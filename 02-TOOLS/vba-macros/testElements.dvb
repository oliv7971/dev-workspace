Attribute VB_Name = "Module1"
Private Sub AcadDocument_SelectionChanged(ByVal SelectionSets As AcadSelectionSets)
    Dim objSelection As AcadSelectionSet
    Dim objEntity As AcadEntity
    Dim objPolyline As AcadLWPolyline
    
    ' Vérifier si une entité a été sélectionnée
    If SelectionSets.Count > 0 Then
        Set objSelection = SelectionSets.Item(0)
        
        ' Boucler à travers les entités sélectionnées
        For Each objEntity In objSelection
            ' Vérifier si l'entité est une polyligne
            If TypeOf objEntity Is AcadLWPolyline Then
                Set objPolyline = objEntity ' Convertir l'entité en polyligne
                MsgBox "Vous avez sélectionné une polyligne avec " & objPolyline.NumberOfVertices & " sommets.", vbInformation, "Polyligne sélectionnée"
                Exit Sub ' Sortir de la boucle après avoir trouvé une polyligne
            End If
        Next objEntity
        ' Aucune polyligne trouvée parmi les entités sélectionnées
        MsgBox "Aucune polyligne n'a été sélectionnée.", vbExclamation, "Sélection de polyligne"
    Else
        ' Aucune entité sélectionnée
        MsgBox "Aucune entité n'a été sélectionnée.", vbExclamation, "Sélection de polyligne"
    End If
End Sub

Sub SelectionnerPolyligne()
    ' Activer les événements de sélection
    ThisDrawing.Application.EnableSingleEvent True
    
    ' Exécuter la commande SSGET
    ThisDrawing.SendCommand "_SSGET" & vbCr & "L " & vbCr
End Sub


Sub Example_Select()
    ' This example adds members to a selection set, first by crossing and
    ' then by filtering for circles.
    
    ' Create the selection set
    Dim ssetObj As AcadSelectionSet
    Set ssetObj = ThisDrawing.SelectionSets.Add("SSET")
    
    
    ' Add all object to the selection set that lie within a crossing of (28,17,0) and
    ' (-3.3, -3.6,0)
    Dim mode As Integer
    Dim corner1(0 To 2) As Double
    Dim corner2(0 To 2) As Double
    
    mode = acSelectionSetCrossing
    corner1(0) = 28: corner1(1) = 17: corner1(2) = 0
    corner2(0) = -3.3: corner2(1) = -3.6: corner2(2) = 0
    ssetObj.Select mode, corner1, corner2
    
    ' Add all the Circles to the selection set that lie within the crossing of (28,17,0) and
    ' (-3.3, -3.6,0) by filtering from the current drawing
    Dim gpCode(0) As Integer
    Dim dataValue(0) As Variant
    gpCode(0) = 0
    dataValue(0) = "Circle"
    
    Dim groupCode As Variant, dataCode As Variant
    groupCode = gpCode
    dataCode = dataValue
    
    ssetObj.Select mode, corner1, corner2, groupCode, dataCode
    
End Sub
  

Sub Example_CopyObjects()
    ' This example creates a Circle object and uses the CopyObjects
    ' method to make a copy of the new Circle.

    Dim DOC1 As AcadDocument
    Dim circleObj1 As AcadCircle, circleObj2 As AcadCircle
    Dim circleObj1Copy As AcadCircle, circleObj2Copy As AcadCircle
    Dim centerPoint(0 To 2) As Double
    Dim radius1 As Double, radius2 As Double
    Dim radius1Copy As Double, radius2Copy As Double
    Dim objCollection(0 To 1) As Object
    Dim retObjects As Variant
    
    ' Define the Circle object
    centerPoint(0) = 0: centerPoint(1) = 0: centerPoint(2) = 0
    radius1 = 5#: radius2 = 7#
    radius1Copy = 1#: radius2Copy = 2#
    
    ' Create a new drawing
    Set DOC1 = Documents.Add
    
    ' Add two circles to the drawing
    Set circleObj1 = DOC1.modelSpace.AddCircle(centerPoint, radius1)
    Set circleObj2 = DOC1.modelSpace.AddCircle(centerPoint, radius2)
    ThisDrawing.Application.ZoomAll
    
    ' Copy objects
    '
    ' First put the objects to be copied into a form compatible with CopyObjects
    Set objCollection(0) = circleObj1
    Set objCollection(1) = circleObj2
    
    ' Copy object and get back a collection of the new objects (copies)
    retObjects = DOC1.CopyObjects(objCollection)
    
    ' Get newly created object and apply new properties to the copies
    Set circleObj1Copy = retObjects(0)
    Set circleObj2Copy = retObjects(1)
    
    circleObj1Copy.radius = radius1Copy
    circleObj2Copy.radius = radius2Copy
        
    ThisDrawing.Application.ZoomAll
    
    MsgBox "Circles copied."
End Sub

'Récupérer les coordonnées d'un point
Sub RecupCoords()

    Dim Point As Variant
    Point = ThisDrawing.Utility.GetPoint(, "Cliquer le point : ")
    Dim x As Double
    x = Point(0)
    Dim y As Double
    y = Point(1)
    Dim Z As Double
    Z = Point(2)

End Sub


'Sélectionner un objet
Sub selectentite()


Dim ent As AcadEntity
Dim pt As Variant
ThisDrawing.Utility.GetEntity ent, pt, "Sélectionner l'objet : "

End Sub

'Exécuter une commande AutoCAD
Sub acadCmd()


Dim Commande As String
Commande = "apropos" & " "
ThisDrawing.SendCommand Commande
End Sub


Sub Open_Dwg()
   On Error Resume Next

   Dim acadApp As AcadApplication
   Dim a As Object

   Set a = GetObject(, "AutoCAD.Application")

   If a Is Nothing Then
      Set a = CreateObject("AutoCAD.Application")

      If a Is Nothing Then
         MsgBox "AutoCAD must be running before performing this action.", vbCritical
         Exit Sub
      End If
   End If

   Set acadApp = a
   acadApp.Visible = True
   Set acadApp.ActiveDocument = acadApp.Documents.Open("<your filename>")
End Sub

Attribute VB_Name = "Module10"
'THIS IS THE CLASS MODULE I WAS GIVEN ON THE AUTOCAD FORUM
Option Explicit

'//The Win32 API Functions///
Private Declare PtrSafe Function GetOpenFileName Lib "comdlg32.dll" _
    Alias "GetOpenFileNameA" (OFN As OPENFILENAME) As Boolean

Private Declare PtrSafe Function GetSaveFileName Lib "comdlg32.dll" _
    Alias "GetSaveFileNameA" (OFN As OPENFILENAME) As Boolean

Private Declare PtrSafe Function FindWindow Lib "user32" _
    Alias "FindWindowA" (ByVal lpClassName As String, _
    ByVal lpWindowName As String) As LongPtr

'//A few of the available Flags///
Private Const OFN_FILEMUSTEXIST = &H1000
Private Const OFN_HIDEREADONLY = &H4
Private Const OFN_ALLOWMULTISELECT = &H200
'This one keeps your dialog from turning into
'A browse by folder dialog if multiselect is true!
'Not sure what I mean? Remove it from the flags
'In the "ShowOpen Open" & "ShowOpen Save" methods.
Private Const OFN_EXPLORER As Long = &H80000
'//The Structure
Private Type OPENFILENAME
    lStructSize As Long
    hwndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As LongPtr
    lpTemplateName As String
End Type


Private lngHwnd As LongPtr
Public strFilter As String
Public strTitle As String
Public strDir As String
Private blnHideReadOnly As Boolean
Private blnAllowMulti As Boolean
Private blnMustExist As Boolean

Private Sub Class_Initialize()
    'Set default values when
    'class is first created
    strDir = Application.ActiveDocument.Path & "\"
    strTitle = "Select Files"
    'strFilter = "Drawing Files" & Chr$(0) & "*.dwg" & Chr$(0)

    lngHwnd = FindWindow(vbNullString, Application.Caption)
    'None of the flags are set here!
End Sub

Public Function FindUserForm(objForm As UserForm) As LongPtr
    Dim lngTemp As LongPtr
    Dim strCaption As String
    strCaption = objForm.Caption
    lngTemp = FindWindow(vbNullString, strCaption)

    If lngTemp <> 0 Then
        FindUserForm = lngTemp
    End If
End Function

Public Property Let OwnerHwnd(ByVal WindowHandle As LongPtr)
    '//FOR YOU TODO//
    'Use the API to validate this handle
    lngHwnd = WindowHandle
    'This value is set at startup to the handle of the
    'AutoCAD Application window, if you want the owner
    'to be a user form you will need to obtain its
    'Handle by using the "FindUserForm" function in
    'This class.
End Property

Public Property Get OwnerHwnd() As LongPtr
    OwnerHwnd = lngHwnd
End Property

Public Property Let Title(ByVal Caption As String)
    'strTitle = "Select Files"
End Property

Public Property Get Title() As String
    'title = strTitle
End Property

Public Property Let Filter(ByVal FilterString As String)
    'Filters change the type of files that are
    'displayed in the dialog. I have designed this
    'validation to use the same filter format the
    'Common dialog OCX uses:
    '"All Files (*.*)|*.*"
    Dim intPos As Integer

    Do While InStr(FilterString, "|") > 0
        intPos = InStr(FilterString, "|")
        If intPos > 0 Then
            FilterString = Left$(FilterString, intPos - 1) _
            & Chr$(0) & Right$(FilterString, _
            Len(FilterString) - intPos)
        End If
    Loop

    If Right$(FilterString, 2) <> Chr$(0) & Chr$(0) Then
        FilterString = FilterString & Chr$(0)
    End If

    'strFilter = FilterString
End Property

Public Property Get Filter() As String
    'Here we reverse the process and return
    'the Filter in the same format the it was
    'entered
    Dim intPos As Integer
    Dim strTemp As String
    strTemp = strFilter

    Do While InStr(strTemp, Chr$(0)) > 0
        intPos = InStr(strTemp, Chr$(0))
        If intPos > 0 Then
            strTemp = Left$(strTemp, intPos - 1) & "|" & Right$(strTemp, _
            Len(strTemp) - intPos)
        End If
    Loop

    If Right$(strTemp, 1) = "|" Then
        strTemp = Left$(strTemp, Len(strTemp) - 1)
    End If

    Filter = strTemp
End Property

Public Property Let StartInDir(ByVal strFolder As String)
    'Sets the directory the dialog displays when called
    If Len(Dir(strFolder)) > 0 Then
        strDir = strFolder
    Else
        Err.Raise 514, "FileDialog", "Invalid Initial Directory"
    End If
End Property

Public Property Let HideReadOnly(ByVal blnVal As Boolean)
    blnHideReadOnly = blnVal
End Property

Public Property Let MultiSelect(ByVal blnVal As Boolean)
    'allow users to select more than one file using
    'The Shift or CTRL keys during selection
    blnAllowMulti = True
End Property

Public Property Let FileMustExist(ByVal blnVal As Boolean)
    blnMustExist = blnVal
End Property

'@~~~~~~~~~~~~~~~~~~~~~~~~~~~~~~~~~~~~~~~~~~~~~~~~@
' Display and use the File open dialog
'@~~~~~~~~~~~~~~~~~~~~~~~~~~~~~~~~~~~~~~~~~~~~~~~~@

Function thAddFilterItem(ByVal strFilter As String, ByVal strDescription As String, Optional ByVal varItem As Variant) As String

    If IsMissing(varItem) Then varItem = "*.*"
    thAddFilterItem = strFilter & strDescription & vbNullChar & varItem & vbNullChar

End Function

Public Function ShowOpen(ByVal strDir As String, ByVal strFilter As String, ByVal strTitle As String) As String

    Dim strTemp As String
    'strFilter = thAddFilterItem(strFilter, "Drawing Files (*.dwg)", "*.dwg")

    Dim udtStruct As OPENFILENAME

    With udtStruct
        .lStructSize = LenB(udtStruct)
        'Use our private variable
        .hwndOwner = lngHwnd
        'Use our private variable
        .lpstrFilter = strFilter
        .lpstrFile = Space$(254)
        .nMaxFile = 255
        .lpstrFileTitle = Space$(254)
        .nMaxFileTitle = 255
        'Use our private variable
        .lpstrInitialDir = strDir
        'Use our private variable
        .lpstrTitle = strTitle
        ' udtStruct.lpstrCustomFilter = "*.*"
        'Ok, here we test our booleans to
        'set the flag
    End With

    If blnHideReadOnly And blnAllowMulti And blnMustExist Then
        udtStruct.flags = OFN_HIDEREADONLY Or _
        OFN_ALLOWMULTISELECT Or OFN_EXPLORER Or OFN_FILEMUSTEXIST
    ElseIf blnHideReadOnly And blnAllowMulti Then
        udtStruct.flags = OFN_ALLOWMULTISELECT _
        Or OFN_EXPLORER Or OFN_HIDEREADONLY
    ElseIf blnHideReadOnly And blnMustExist Then
        udtStruct.flags = OFN_HIDEREADONLY Or OFN_FILEMUSTEXIST
    ElseIf blnAllowMulti And blnMustExist Then
        udtStruct.flags = OFN_ALLOWMULTISELECT Or _
        OFN_EXPLORER Or OFN_FILEMUSTEXIST
    ElseIf blnHideReadOnly Then
        udtStruct.flags = OFN_HIDEREADONLY
    ElseIf blnAllowMulti Then
        udtStruct.flags = OFN_ALLOWMULTISELECT _
        Or OFN_EXPLORER
    ElseIf blnMustExist Then
        udtStruct.flags = OFN_FILEMUSTEXIST
    End If

    If GetOpenFileName(udtStruct) Then
        strTemp = (Trim(udtStruct.lpstrFile))
        ShowOpen = Mid(strTemp, 1, Len(strTemp) - 1)
    End If

End Function

'@~~~~~~~~~~~~~~~~~~~~~~~~~~~~~~~~~~~~~~~~~~~~~~~~@
' Display and use the File Save dialog
'@~~~~~~~~~~~~~~~~~~~~~~~~~~~~~~~~~~~~~~~~~~~~~~~~@
Public Function ShowSave(ByVal strDir As String, ByVal strFilter, ByVal strTitle) As String

    Dim strTemp As String
    Dim udtStruct As OPENFILENAME
    udtStruct.lStructSize = LenB(udtStruct)
    'Use our private variable
    udtStruct.hwndOwner = lngHwnd
    'Use our private variable
    udtStruct.lpstrFilter = strFilter
    udtStruct.lpstrFile = Space$(254)
    udtStruct.nMaxFile = 255
    udtStruct.lpstrFileTitle = Space$(254)
    udtStruct.nMaxFileTitle = 255
    'Use our private variable
    udtStruct.lpstrInitialDir = strDir
    'Use our private variable
    udtStruct.lpstrTitle = strTitle
    If blnMustExist Then
        udtStruct.flags = OFN_FILEMUSTEXIST
    End If

    If GetSaveFileName(udtStruct) Then
        strTemp = (Trim(udtStruct.lpstrFile))
        ShowSave = Mid(strTemp, 1, Len(strTemp) - 1)
    End If

End Function

Function GetXLSFile(ByVal strDir As String, ByVal strTitle As String)
   ' strTitle = "Select Excel File"
    Dim strFilter As String ' , strTitle As String
    Dim lngFlags As LongPtr, filestring
    strFilter = thAddFilterItem(strFilter, "Excel File (*.xls)", "*.xls")
    GetXLSFile = ShowOpen(strDir, strFilter, strTitle)
End Function

Function GetDWGFile(ByVal strDir As String, ByVal strTitle As String)
   ' strTitle = "Select Drawing File"
    Dim strFilter As String ' , strTitle As String
    Dim lngFlags As LongPtr, filestring
    strFilter = thAddFilterItem(strFilter, "DWG File (*.dwg)", "*.dwg")
    GetDWGFile = ShowOpen(strDir, strFilter, strTitle)
End Function

Function SaveFile() '
    Dim strTitle As String
    Dim strDir As String
    Dim strFilter As String ' , strTitle As String
    Dim lngFlags As LongPtr, filestring
    strDir = "c:\"
    strTitle = "Save File"
    strFilter = thAddFilterItem(strFilter, "txt File (*.txt)", "*.txt")
    'SaveFile = ShowSave(strDir, strFilter, strTitle)
End Function

Attribute VB_Name = "Module11"
'THIS IS MY PRIMARY MODULE
Public Sub OpenFile()

    Set objFile = New FileDialogs

    Dim initpath As String
    Dim initfilter As String

    Dim inittitle As String

    initpath = ThisDrawing.Path & "\"
    'initfilter = "Drawing Files (*.dwg)|*.dwg"
    inittitle = "Select Files"

    'objFile.OwnerHwnd = ThisDrawing.Hwnd
    'objFile.title = "Select Drawings"
    objFile.MultiSelect = True
    'objFile.Filter = initfilter
    'objFile.StartInDir = initpath

    strFileName = objFile.ShowOpen(initpath, initfilter, inittitle)

    If Not strFileName = vbNullString Then
        MsgBox strFileName
    End If

    Set objFile = Nothing

End Sub

Sub CreateText()
    Dim XLnCADText As AcadText
    Dim InsPoint(0 To 2) As Double
    Dim Height As Double
    Dim Content As String
    InsPoint(0) = 300#: InsPoint(1) = 450#: InsPoint(2) = 0
    Height = 10
    Content = "XL n CAD"
    Set XLnCADText = ThisDrawing.modelSpace.AddText(Content, InsPoint, Height)
    XLnCADText.Rotation = (25 * 3.14) / 180
    ZoomAll
End Sub


Sub ExtractDetailsOfAutoCADPoints()
    Open "c:\data\temp\ExtractedDetails.Txt" For Output As 1
    Dim x, y, Z As Double
    Dim XLnCADObject As AcadObject
    Dim XLnCADPoint As AcadPoint
    For Each XLnCADObject In ThisDrawing.modelSpace
        If XLnCADObject.ObjectName = “AcadPoint” Then
            Set XLnCADPoint = XLnCADObject
            x = XLnCADPoint.coordinates(0)
            y = XLnCADPoint.coordinates(1)
            Z = XLnCADPoint.coordinates(2)
            Print #1, x; y; Z; “” & XLnCADPoint.Layer
        End If
    Next
    Close (1)
End Sub

Attribute VB_Name = "Module12"

'-----------------------------------
' importer les profils de norvege situés dans un repertoire
' dans le fichier dwg actuellement ouvert
' l'import commence par renommer les fichiers dans windows pour garder que le PM
' il demande d'ouvrir un repertoire par une methode freestyle , j'arrive pas à utiliser les filedialog
' chaque contenu est censé se décaler de 25 (parametrable) mais ca marche pas , ca s'insere à 0,0
'-----------------------------------
Sub ImporterDXFDansAutoCAD()
    Dim cheminRepertoire As String
    Dim fichierDXF As String
    Dim docActif As Document
    Dim prefixe As String
    Dim suffixe As String
    Dim importFile As String
    Dim InsertPoint(0 To 2) As Double
    Dim basepoint(0 To 2) As Double
    Dim baseoffset(0 To 2) As Double
    Dim zeroPt(0 To 2)
    Dim scalefactor As Double
    Dim compteur As Double
    Dim fileName As String
    Dim extensionIndex As Long
    Dim newTextPosition(0 To 2) As Double
    Dim modelName As AcadModelSpace
    Dim newText As AcadText
    
    ' prefixe des noms de profils (VERIFIER QUE C EST TJS LE MEME) : A ADAPTER
    prefixe = "ProfileStation"
    ' supprimer le suffixe (optionnel si on peut supprimer tout ce qu'il y a apres l'espace" : A ADAPTER
    suffixe = ""
    
    ' init du pt insertion
    InsertPoint(0) = 0#: InsertPoint(1) = 0#: InsertPoint(2) = 0#
    zeroPt(0) = 0#: zeroPt(1) = 0#: zeroPt(2) = 0#
    ' position du 1er profil à importer : A ADAPTER
    basepoint(0) = 0#: basepoint(1) = 0#: basepoint(2) = 0#
    ' valeur du decalage entre profils : A ADAPTER
    baseoffset(0) = 25#: baseoffset(1) = 0#: baseoffset(2) = 0#
    ' c'est pour passer les fonctions , on retouche pas
    scalefactor = 1#
    compteur = 0#

    ' Demander à l'utilisateur de choisir un répertoire
    cheminRepertoire = SelectFolder("Sélectionnez un répertoire contenant des fichiers DXF", "")

    ' Vérifier si un répertoire a été sélectionné
    If cheminRepertoire <> "" Then
        ' Ouvrir le fichier AutoCAD actif
        If ThisDrawing.Application.ActiveDocument Is Nothing Then
            MsgBox "Aucun fichier AutoCAD ouvert. Veuillez ouvrir un fichier AutoCAD et réessayer.", vbExclamation
            Exit Sub
        End If

    
    ' Boucler à travers tous les fichiers .dxf dans le répertoire pour supprimer les espaces qui peuvent causer soucis
    ' en profiter pour renommer les profils avec noms à rallonge , pour garder surtout le PM
    fichier = Dir(cheminRepertoire & "\*.dxf")
    Do While fichier <> ""
        ' Construire le nouveau nom du fichier en supprimant le préfixe, le suffixe et tout ce qui se trouve après le premier espace
        nouveauNom = fichier
        If prefixe <> "" Then
            If Left(nouveauNom, Len(prefixe)) = prefixe Then
                nouveauNom = Mid(nouveauNom, Len(prefixe) + 1)
            End If
        End If
        If suffixe <> "" Then
            If InStr(nouveauNom, suffixe) > 0 Then
                nouveauNom = Left(nouveauNom, InStr(nouveauNom, suffixe) - 1)
            End If
        End If
        espaceIndex = InStr(nouveauNom, " ")
        If espaceIndex > 0 Then
            nouveauNom = Left(nouveauNom, espaceIndex - 1)
        End If
        
        ' Renommer le fichier
        If InStrRev(nouveauNom, ".") = 0 Then
            Name cheminRepertoire & "\" & fichier As cheminRepertoire & "\" & nouveauNom & ".dxf"
        Else
            Name cheminRepertoire & "\" & fichier As cheminRepertoire & "\" & nouveauNom
        End If
        
        ' Passer au fichier suivant
        fichier = Dir
    Loop


        ' Boucler à travers tous les fichiers DXF dans le répertoire sélectionné , mais qui ont un nouveau nom
        ' donc faut relancer la commande pour renouveler la liste
        fichierDXF = Dir(cheminRepertoire & "\*.dxf")
        Do While fichierDXF <> ""
            ' Importer le contenu du fichier DXF dans le fichier AutoCAD actif
            ' en essayant de decaler le contenu , mais CA DECALE PAS GRAND CHOSE
            importFile = cheminRepertoire & "\" & fichierDXF
            InsertPoint(0) = basepoint(0) + baseoffset(0) * compteur
            InsertPoint(1) = basepoint(1) + baseoffset(1) * compteur
            InsertPoint(2) = basepoint(2) + baseoffset(2) * compteur
            ThisDrawing.Import importFile, InsertPoint, scalefactor
            
            
            ' Récupérer le nom de fichier sans extension pour faire un texte au dessus du profil
            extensionIndex = InStrRev(fichierDXF, ".")
            If extensionIndex > 0 Then
                fileName = Left(fichierDXF, extensionIndex - 1)
            Else
                fileName = fichierDXF ' Utiliser le nom complet si aucune extension n'est trouvée
            End If
            
            ' Ajouter un texte avec le nom du fichier importé (sans extension)
            Set modelName = ThisDrawing.modelSpace
            
            
            ' Déplacer le texte vers le haut de 10 mètres (ON POURRAIT METTRE UNE VARIABLE D'AILLEURS)
            newTextPosition(0) = InsertPoint(0)
            newTextPosition(1) = InsertPoint(1) + 10
            newTextPosition(2) = InsertPoint(2)
            Set newText = modelName.AddText(fileName, newTextPosition, 1)
            ' on passe au fichier dxf suivant
            fichierDXF = Dir
            compteur = compteur + 1#

        Loop

        MsgBox "Importation terminée avec succès !", vbInformation
    End If
End Sub

'-----------------------------------
' solution contournement pour selectionner un repertoire
' reste à trouver comment on fait pour un fichier seul
'-----------------------------------

Function SelectFolder(Optional Title As String, Optional TopFolder As String) As String
    Dim objShell As Object
    Dim objFolder As Object

    On Error Resume Next
    Set objShell = CreateObject("Shell.Application")
    Set objFolder = objShell.BrowseForFolder(0, Title, 0, TopFolder)
    If Not objFolder Is Nothing Then
        SelectFolder = objFolder.Items.Item.Path
    End If
End Function

Attribute VB_Name = "Module13"
'//Available Flags///
Private Const OFN_ALLOWMULTISELECT = &H200
Private Const OFN_CREATEPROMPT = &H2000
Private Const OFN_ENABLEHOOK = &H20
Private Const OFN_ENABLETEMPLATE = &H40
Private Const OFN_ENABLETEMPLATEHANDLE = &H80
Private Const OFN_EXPLORER = &H80000                         '  new look commdlg
Private Const OFN_EXTENSIONDIFFERENT = &H400
Private Const OFN_FILEMUSTEXIST = &H1000
Private Const OFN_HIDEREADONLY = &H4
Private Const OFN_LONGNAMES = &H200000                       '  force long names for 3.x modules
Private Const OFN_NOCHANGEDIR = &H8
Private Const OFN_NODEREFERENCELINKS = &H100000
Private Const OFN_NOLONGNAMES = &H40000                      '  force no long names for 4.x modules
Private Const OFN_NONETWORKBUTTON = &H20000
Private Const OFN_NOREADONLYRETURN = &H8000
Private Const OFN_NOTESTFILECREATE = &H10000
Private Const OFN_NOVALIDATE = &H100
Private Const OFN_OVERWRITEPROMPT = &H2
Private Const OFN_PATHMUSTEXIST = &H800
Private Const OFN_READONLY = &H1
Private Const OFN_SHAREAWARE = &H4000
Private Const OFN_SHAREFALLTHROUGH = 2
Private Const OFN_SHARENOWARN = 1
Private Const OFN_SHAREWARN = 0
Private Const OFN_SHOWHELP = &H10

'private class variables

#If VBA7 Then
Private lngHwnd As LongPtr
#Else
Private lngHwnd As Long
#End If

Private strFilter As String
Private strTitle As String
Private strDir As String
Private strFile As String   'elj
Private lngSelectedFilter As Long
Private blnHideReadOnly As Boolean
Private blnMode As Boolean

Private Sub Class_Initialize()
  'Set default values when
  'class is first created
  strDir = CurDir
  strTitle = "Llamas Rule"
  strFile = ""
  strFilter = "All Files" _
  & Chr$(0) & "*.*" & Chr$(0)
  lngSelectedFilter = 0
  lngHwnd = &O0 'Desktop
End Sub

#If VBA7 Then
Public Property Let OwnerHwnd(WindowHandle As LongPtr)
  lngHwnd = WindowHandle
End Property
#Else
Public Property Let OwnerHwnd(WindowHandle As Long)
  '//FOR YOU TODO//
  'Use the API to validate this handle
  lngHwnd = WindowHandle
  'R14 users who just want to use this code:
  'Simple, don't set this property! the default
  'of &0 will work fine for most of your needs
End Property
#End If

#If VBA7 Then
Public Property Get OwnerHwnd() As LongPtr
  OwnerHwnd = lngHwnd
End Property
#Else
Public Property Get OwnerHwnd() As Long
  OwnerHwnd = lngHwnd
End Property
#End If
'elj added property
Public Property Let MultiSelect(mode As Boolean)
    blnMode = mode
End Property


'elj added property
Public Property Get MultiSelect() As Boolean
  MultiSelect = blnMode
End Property
Public Property Get SelectedFilter() As Long
  SelectedFilter = lngSelectedFilter
End Property


Public Property Let SelectedFilter(FilterNumber As Long)
  lngSelectedFilter = FilterNumber
End Property

'elj added property
Public Property Let StartFile(fileName As String)
  'don't allow null strings
  If Not fileName = vbNullString Then
    strFile = fileName
  End If
End Property

'elj added property
Public Property Get StartFile() As String
  StartFile = strFile
End Property

Public Property Let StartInDir(StartDir As String)
  'don't allow null strings
  If Not StartDir = vbNullString Then
    strDir = StartDir
  End If
End Property

Public Property Get StartInDir() As String
  StartInDir = strDir
End Property

Public Property Let Title(Caption As String)
  'don't allow null strings
  If Not Caption = vbNullString Then
    strTitle = Caption
  End If
End Property

Public Property Get Title() As String
  Title = strTitle
End Property

Public Property Let Filter(ByVal FilterString As String)
  'Filters change the type of files that are
  'displayed in the dialog. I have designed this
  'validation to use the same filter format the
  'Common dialog OCX uses:
  '"All Files (*.*)|*.*"
  Dim intPos As Integer
  Do While InStr(FilterString, "|") > 0
    intPos = InStr(FilterString, "|")
    If intPos > 0 Then
      FilterString = Left$(FilterString, intPos - 1) _
      & Chr$(0) & Right$(FilterString, _
      Len(FilterString) - intPos)
    End If
  Loop
  If Right$(FilterString, 2) <> Chr$(0) & Chr$(0) Then
    FilterString = FilterString & Chr$(0)
  End If
  strFilter = FilterString
End Property


Public Property Get Filter() As String
  'Here we reverse the process and return
  'the Filter in the same format that it was
  'entered
  Dim intPos As Integer
  Dim strTemp As String
  strTemp = strFilter
  Do While InStr(strTemp, Chr$(0)) > 0
    intPos = InStr(strTemp, Chr$(0))
    If intPos > 0 Then
      strTemp = Left$(strTemp, intPos - 1) _
      & "|" & Right$(strTemp, _
      Len(strTemp) - intPos)
    End If
  Loop
  If Right$(strTemp, 1) = "|" Then
    strTemp = Left$(strTemp, Len(strTemp) - 1)
  End If
  Filter = strTemp
End Property

Public Property Let HideReadOnly(blnVal As Boolean)
  'Simple one
  blnHideReadOnly = blnVal
End Property

Public Property Get HideReadOnly() As Boolean
  HideReadOnly = blnHideReadOnly
End Property

'@~~~~~~~~~~~~~~~~~~~~~~~~~~~~~~~~~~~~~~~~~~~~~~~~@
' Display and use the File open dialog
'@~~~~~~~~~~~~~~~~~~~~~~~~~~~~~~~~~~~~~~~~~~~~~~~~@
Public Function ShowOpen() As String
  Dim strTemp As String
  Dim udtStruct As OPENFILENAME
  udtStruct.lStructSize = Len(udtStruct)
  'Use our private variable
  udtStruct.hwndOwner = lngHwnd
  'Use our private variable
  udtStruct.lpstrFilter = strFilter
  udtStruct.nFilterIndex = lngSelectedFilter
  'elj start
'  udtStruct.lpstrFile = Space$(254)    elj comment out
  If Not strFile = vbNullString Then
    udtStruct.lpstrFile = strFile & Space(254 - Len(strFile))
  Else
    udtStruct.lpstrFile = Space$(254)
  End If
  'elj end
  udtStruct.nMaxFile = 255
  udtStruct.lpstrFileTitle = Space$(254)
  udtStruct.nMaxFileTitle = 255
  'Use our private variable
  udtStruct.lpstrInitialDir = strDir
  'Use our private variable
  udtStruct.lpstrTitle = strTitle
  'Ok, here we test our boolean to
  'set the flags
  udtStruct.flags = 0
  If blnHideReadOnly Then udtStruct.flags = OFN_HIDEREADONLY + udtStruct.flags
  If blnMode Then udtStruct.flags = OFN_ALLOWMULTISELECT + udtStruct.flags
  If GetOpenFileName(udtStruct) Then
    strTemp = (Trim(udtStruct.lpstrFile))
    ShowOpen = Mid(strTemp, 1, Len(strTemp) - 1)
  End If
End Function

'@~~~~~~~~~~~~~~~~~~~~~~~~~~~~~~~~~~~~~~~~~~~~~~~~@
' Display and use the File Save dialog
'@~~~~~~~~~~~~~~~~~~~~~~~~~~~~~~~~~~~~~~~~~~~~~~~~@
Public Function ShowSave() As String
    Dim strTemp As String
  Dim udtStruct As OPENFILENAME
  udtStruct.lStructSize = Len(udtStruct)
  'Use our private variable
  udtStruct.hwndOwner = lngHwnd
  'Use our private variable
  udtStruct.lpstrFilter = strFilter
'  udtStruct.lpstrFile = Space$(254)    'elj comment out
  'elj start
  If Not strFile = vbNullString Then
    udtStruct.lpstrFile = strFile & Space(254 - Len(strFile))
  Else
    udtStruct.lpstrFile = Space$(254)
  End If
  'elj end
  udtStruct.nMaxFile = 255
  udtStruct.lpstrFileTitle = Space$(254)
  udtStruct.nMaxFileTitle = 255
  'Use our private variable
  udtStruct.lpstrInitialDir = strDir
  'Use our private variable
  udtStruct.lpstrTitle = strTitle
  'Ok, here we test our flag
  If blnHideReadOnly Then
    udtStruct.flags = OFN_HIDEREADONLY
  Else
    udtStruct.flags = 0
  End If
  If GetSaveFileName(udtStruct) Then
    strTemp = (Trim(udtStruct.lpstrFile))
    ShowSave = Mid(strTemp, 1, Len(strTemp) - 1)
  End If
End Function

Sub UtiliserBoiteDialogue()
    ' Créer une instance de la classe BoiteDialogueFichier
  '  Dim boiteDialogue As New BoiteDialogueFichier
    
    ' Définir les propriétés de la boîte de dialogue
 '   boiteDialogue.Title = "Sélectionnez un fichier"
  '  boiteDialogue.Filter = "Fichiers texte (*.txt)|*.txt|Tous les fichiers (*.*)|*.*"
  '  boiteDialogue.StartInDir = "C:\Users\Utilisateur\Documents"
    
    ' Afficher la boîte de dialogue de sélection de fichiers
    Dim cheminFichier As String
    cheminFichier = ShowOpen
    
    ' Vérifier si un fichier a été sélectionné
    If cheminFichier <> "" Then
        ' Faire quelque chose avec le fichier sélectionné
        MsgBox "Vous avez sélectionné le fichier : " & cheminFichier
    Else
        MsgBox "Aucun fichier sélectionné."
    End If
End Sub

Attribute VB_Name = "Module14"
Sub CopyObjectsFromActiveFileToAnother3()
    Dim targetDoc As AcadDocument
    Dim objSelection As AcadSelectionSet
    Dim obj As AcadObject
    Dim objCollection As Object
    Dim selectedObjects() As AcadObject
    Dim returnObj As AcadObject
    Dim basePnt As Variant

    Dim objPolyline As AcadLWPolyline
    Dim objText As AcadText
    Dim objPoint As AcadPoint
    Dim i As Integer
    
    Dim DestinationFolder As String
    Dim fileName As String
    Dim filePath As String
    
    Dim doc As Object
    Dim chemin As String
    
    Dim countSelectedObjects As Integer
    
    DestinationFolder = "c:\data\temp"
    fileName = "fichierCible.dwg"
    filePath = ""
    countSelectedObjects = 0
    
    ' Créer un jeu de sélection pour les objets à copier
    On Error Resume Next
    ThisDrawing.SelectionSets.Item("CopySelection").Delete
    On Error GoTo 0
    Set objSelection = ThisDrawing.SelectionSets.Add("CopySelection")
    
    ' Demander à l'utilisateur de sélectionner des objets
   ' ThisDrawing.Utility.GetSelection objSelection, selectedObjects

    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            ReDim selectedObjects(1 To 1) As AcadObject
            Set selectedObjects(1) = objPolyline
            MsgBox "Vous avez sélectionné une polyligne.", vbInformation, "Polyligne sélectionnée"
        Else
            MsgBox "L'entité sélectionnée n'est pas une polyligne.", vbExclamation, "Sélection de polyligne"
        End If
    Else
        MsgBox "Aucune entité n'a été sélectionnée.", vbExclamation, "Sélection de polyligne"
    End If
    
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            fileName = objText.TextString
            MsgBox "Vous avez sélectionné un texte : " & objText.TextString, vbInformation, "Texte sélectionné"
        Else
            MsgBox "L'entité sélectionnée n'est pas un texte.", vbExclamation, "Sélection de texte"
        End If
    Else
        MsgBox "Aucune entité n'a été sélectionnée.", vbExclamation, "Sélection de texte"
    End If
    
    ' Demander à l'utilisateur de sélectionner un point
    ThisDrawing.Utility.GetEntity returnObj, basePnt, "Sélectionnez un point:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point.", vbInformation, "Point sélectionné"
        Else
            MsgBox "L'entité sélectionnée n'est pas un point.", vbExclamation, "Sélection de point"
        End If
    Else
        MsgBox "Aucune entité n'a été sélectionnée.", vbExclamation, "Sélection de point"
    End If
    
    ' Vérifier s'il y a des objets sélectionnés
    countSelectedObjects = UBound(selectedObjects) + 1
    If countSelectedObjects = 0 Then
        MsgBox "Aucun objet sélectionné.", vbExclamation
        Exit Sub
    End If
    
   
End Sub


Sub CreerNouveauDXF()
    Dim doc As Object
    Dim chemin As String
    
    ' Créer une nouvelle instance d'AutoCAD
    Set doc = CreateObject("AutoCAD.Application")
    
    ' Activer AutoCAD
    doc.Visible = True
    
    ' Créer un nouveau dessin
    doc.Documents.Add
    
    ' Chemin et nom du fichier DXF à enregistrer
    chemin = "C:\data\temp\NouveauFichier.dxf"
    
    ' Enregistrer le dessin au format DXF
    doc.ActiveDocument.SaveAs chemin, 12 ' 12 correspond au format DXF
    
    ' Fermer AutoCAD
    doc.Quit
End Sub


Sub CopyObjectsFromActiveFileToAnother4()
    Dim targetDoc As AcadDocument
    Dim objSelection As AcadSelectionSet
    Dim obj As AcadObject
    Dim objCollection As Object
    Dim selectedObjects() As AcadObject
    Dim returnObj As AcadObject
    Dim basePnt As Variant
    Dim sourcePolyline As AcadLWPolyline

    Dim objPolyline As AcadLWPolyline
    Dim objText As AcadText
    Dim objPoint As AcadPoint
    Dim i As Integer
    
    Dim DestinationFolder As String
    Dim fileName As String
    Dim filePath As String
    
    Dim doc As Object
    Dim chemin As String
    
    Dim deltaX As Double, deltaY As Double
    
    Dim countSelectedObjects As Integer
    
    DestinationFolder = "c:\data\temp"
    fileName = ""
    filePath = ""
    countSelectedObjects = 0
       
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            fileName = objText.TextString
            MsgBox "Vous avez sélectionné un texte : " & fileName, vbInformation, "Texte sélectionné"
        Else
            MsgBox "L'entité sélectionnée n'est pas un texte.", vbExclamation, "Sélection de texte"
            Exit Sub
        End If
    Else
        MsgBox "Aucune entité n'a été sélectionnée.", vbExclamation, "Sélection de texte"
        Exit Sub
    End If
    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            Set sourcePolyline = returnObj ' Convertir l'entité en polyligne
            MsgBox "Vous avez sélectionné une polyligne.", vbInformation, "Polyligne sélectionnée"
        Else
            MsgBox "L'entité sélectionnée n'est pas une polyligne.", vbExclamation, "Sélection de polyligne"
            Exit Sub
        End If
    Else
        MsgBox "Aucune entité n'a été sélectionnée.", vbExclamation, "Sélection de polyligne"
        Exit Sub
    End If
    
    ' Demander à l'utilisateur de sélectionner un point pour l'insertion
    ThisDrawing.Utility.GetEntity returnObj, basePnt, "Sélectionnez un point pour l'insertion:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point pour l'insertion.", vbInformation, "Point sélectionné"
        Else
            MsgBox "L'entité sélectionnée n'est pas un point.", vbExclamation, "Sélection de point"
            Exit Sub
        End If
    Else
        MsgBox "Aucune entité n'a été sélectionnée.", vbExclamation, "Sélection de point"
        Exit Sub
    End If
    
    filePath = DestinationFolder & "\" & fileName & ".dxf"
        ' Calculez les différences entre les coordonnées du point de base sélectionné et (0,0)
    deltaX = 0 - objPoint.coordinates(0)
    deltaY = 0 - objPoint.coordinates(1)
    
    ' Créez un nouveau fichier DXF
    Set targetDoc = ThisDrawing.Application.Documents.Add(True) ' True pour créer un fichier DXF
    
    Dim coordinates As Variant
    coordinates = sourcePolyline.coordinates
    
    Dim numVertices As Integer
    numVertices = UBound(coordinates) / 2 + 1
    
    For i = 0 To numVertices - 1
        ' Obtenir les coordonnées actuelles du sommet
        Dim x As Double
        Dim y As Double
        x = coordinates(i * 2)
        y = coordinates(i * 2 + 1)
        
        ' Ajouter les deltas aux coordonnées
        x = x + deltaX
        y = y + deltaY
        
        ' Mettre à jour les nouvelles coordonnées dans le tableau
        coordinates(i * 2) = x
        coordinates(i * 2 + 1) = y
    Next i

    ' Affecter les nouvelles coordonnées à la polyligne
    sourcePolyline.coordinates = coordinates
    
    ' Copiez la polyligne ajustée dans le nouveau fichier DXF
    Set newPolyline = targetDoc.modelSpace.AddLightWeightPolyline(sourcePolyline.coordinates)
    
    ' Sauvegardez le fichier DXF
    targetDoc.SaveAs filePath, ac2007_dxf  ' Spécifiez le format de fichier DXF
    
    ' Fermez le fichier DXF
    targetDoc.Close
End Sub

Sub CopyPolylineToNewDXF()
    Dim sourceDoc As AcadDocument
    Dim targetDoc As AcadDocument
    Dim sourcePolyline As AcadLWPolyline
    Dim copiedPolyline As AcadEntity
    Dim pastePoint As Variant
    Dim newPath As String

    ' Ouvrir le document source (fichier actif)
    Set sourceDoc = ThisDrawing.Application.ActiveDocument
    
    ' Demander à l'utilisateur de sélectionner une polyligne dans le document source
    On Error Resume Next ' Gérer le cas où rien n'est sélectionné
    Set sourcePolyline = sourceDoc.SelectionSets.Item("SS1").Item(0)
    On Error GoTo 0 ' Réactiver les erreurs
    
    If sourcePolyline Is Nothing Or Not TypeOf sourcePolyline Is AcadLWPolyline Then
        MsgBox "Sélectionnez une polyligne valide dans le document source.", vbExclamation
        Exit Sub
    End If
    
    ' Créer un nouveau document temporaire
    Set targetDoc = ThisDrawing.Application.Documents.Add(True)
    
    ' Copier la polyligne depuis le document source vers le document temporaire
    sourcePolyline.Copy
    targetDoc.SendCommand "_pasteclip" & vbCrLf
    
    ' Sélectionner la polyligne collée
    Set copiedPolyline = targetDoc.modelSpace.Item(targetDoc.modelSpace.Count - 1)
    
    ' Déplacer la polyligne vers (0,0) dans le document temporaire
    pastePoint = copiedPolyline.InsertionPoint
    copiedPolyline.MoveToArray Array(0, 0, 0), pastePoint
    
    ' Enregistrer le document temporaire en format DXF
    newPath = "C:\data\temp\TempPolyline.dxf"
    targetDoc.SaveAs newPath, acDXF
    
    ' Fermer le document temporaire
    targetDoc.Close
    
    MsgBox "La polyligne a été copiée dans le fichier DXF temporaire : " & newPath, vbInformation
End Sub

Attribute VB_Name = "Module15"
Sub CopyObjectsFromActiveFileToAnother5()
    Dim targetDoc As AcadDocument
    Dim objSelection As AcadSelectionSet
    Dim obj As AcadObject
    Dim objCollection As Object
    Dim selectedObjects() As AcadObject
    Dim returnObj As AcadObject
    Dim basePnt As Variant
    Dim sourcePolyline As AcadLWPolyline

    Dim objPolyline As AcadLWPolyline
    Dim objText As AcadText
    Dim objPoint As AcadPoint
    Dim i As Integer
    
    Dim DestinationFolder As String
    Dim fileName As String
    Dim filePath As String
    
    Dim doc As Object
    Dim chemin As String
    
    Dim deltaX As Double, deltaY As Double
    
    Dim countSelectedObjects As Integer
    
    DestinationFolder = "c:\data\temp"
    fileName = ""
    filePath = ""
    countSelectedObjects = 0
       
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            fileName = objText.TextString
            MsgBox "Vous avez sélectionné un texte : " & fileName, vbInformation, "Texte sélectionné"
        Else
            MsgBox "L'entité sélectionnée n'est pas un texte.", vbExclamation, "Sélection de texte"
            Exit Sub
        End If
    Else
        MsgBox "Aucune entité n'a été sélectionnée.", vbExclamation, "Sélection de texte"
        Exit Sub
    End If
    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            Set sourcePolyline = returnObj ' Convertir l'entité en polyligne
            MsgBox "Vous avez sélectionné une polyligne.", vbInformation, "Polyligne sélectionnée"
        Else
            MsgBox "L'entité sélectionnée n'est pas une polyligne.", vbExclamation, "Sélection de polyligne"
            Exit Sub
        End If
    Else
        MsgBox "Aucune entité n'a été sélectionnée.", vbExclamation, "Sélection de polyligne"
        Exit Sub
    End If
    
    ' Demander à l'utilisateur de sélectionner un point pour l'insertion
    ThisDrawing.Utility.GetEntity returnObj, basePnt, "Sélectionnez un point pour l'insertion:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point pour l'insertion.", vbInformation, "Point sélectionné"
        Else
            MsgBox "L'entité sélectionnée n'est pas un point.", vbExclamation, "Sélection de point"
            Exit Sub
        End If
    Else
        MsgBox "Aucune entité n'a été sélectionnée.", vbExclamation, "Sélection de point"
        Exit Sub
    End If
    
    filePath = DestinationFolder & "\" & fileName & ".dxf"
        ' Calculez les différences entre les coordonnées du point de base sélectionné et (0,0)
    deltaX = 0 - objPoint.coordinates(0)
    deltaY = 0 - objPoint.coordinates(1)
    
    ' Créez un nouveau fichier DXF
    Set targetDoc = ThisDrawing.Application.Documents.Add(True) ' True pour créer un fichier DXF
    
    Dim coordinates As Variant
    coordinates = sourcePolyline.coordinates
    
    Dim numVertices As Integer
    numVertices = UBound(coordinates) / 2 + 1
    
    For i = 0 To numVertices - 1
        ' Obtenir les coordonnées actuelles du sommet
        Dim x As Double
        Dim y As Double
        x = coordinates(i * 2)
        y = coordinates(i * 2 + 1)
        
        ' Ajouter les deltas aux coordonnées
        x = x + deltaX
        y = y + deltaY
        
        ' Mettre à jour les nouvelles coordonnées dans le tableau
        coordinates(i * 2) = x
        coordinates(i * 2 + 1) = y
    Next i

    ' Affecter les nouvelles coordonnées à la polyligne
    sourcePolyline.coordinates = coordinates
   ' Copiez la polyligne ajustée dans le nouveau fichier DXF
    Set newPolyline = targetDoc.modelSpace.AddLightWeightPolyline(sourcePolyline.coordinates)
    ' Ajouter le dernier segment pour fermer la polyligne
    
    ' Ajouter le dernier segment pour fermer la polyligne
    newPolyline.AddVertex sourcePolyline.coordinates(0), sourcePolyline.coordinates(1)

    ' Récupérer tous les bulges de la première polyligne
    Dim bulges() As Double
    ReDim bulges(numVertices - 1)

    For i = 0 To numVertices - 1
        bulges(i) = sourcePolyline.GetBulge(i)
    Next i
    
    ' Réaffecter les bulges à la nouvelle polyligne
    For i = 0 To UBound(bulges)
        newPolyline.SetBulge i, bulges(i)
    Next i
        
    ' Sauvegardez le fichier DXF
    targetDoc.SaveAs filePath, ac2007_dxf  ' Spécifiez le format de fichier DXF
    
    ' Fermez le fichier DXF
    targetDoc.Close
End Sub

Attribute VB_Name = "Module16"
'----------------------------------------
' ExportProfilsPline()
' exporte une polyligne de profil dans un fichier dxf
' - demande à l'utilisateur de choisir un texte : typiquement le PM , servira pour construite le nom du fichier
' - demande à l'utilisateur de selectionner une polyligne
' - demande à l'utilisateur de selectionner un point (qui servira de point de base)
' - recupère les éléments de la polyligne
' - récupere les décalages à l'origine
' - recrée une polyligne avec les décalages et la met dans le fichier d'origine
' - reaffecte les arrondis entre les sommets et ferme la polyligne
' - le fichier dxf portera automatiquement le nom equivalent au texte selectionné
' - ATTENTION : ENCORE EN MODE DEVELOPPEMENT : gere pas bien le fait qu'il y ait plusieurs fichiers ouverts au moment du lancement
'----------------------------------------
Sub ExportProfilsPline()
    Dim targetDoc As AcadDocument
    Dim returnObj As AcadObject
    Dim basePnt As Variant
    Dim sourcePolyline As AcadLWPolyline
    Dim newPolyline As AcadLWPolyline
    Dim objPolyline As AcadLWPolyline
    Dim objText As AcadText
    Dim objPoint As AcadPoint
    Dim i As Integer
    Dim DestinationFolder As String
    Dim fileName As String
    Dim filePath As String
    Dim deltaX As Double, deltaY As Double
    Dim bulges() As Double
    Dim x As Double
    Dim y As Double
    Dim nVertex(0 To 1) As Double
    
    ' CONFIGURER ICI LE REPERTOIRE OU SERONT GENERES LES DXF
    DestinationFolder = "c:\data\temp"
    fileName = ""
    filePath = ""
       
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            fileName = objText.TextString
            MsgBox "Vous avez sélectionné un texte : " & vbCrLf & fileName, vbInformation, "Texte sélectionné"
        Else
            MsgBox "L'entité sélectionnée n'est pas un texte.", vbExclamation, "Sélection de texte"
            Exit Sub
        End If
    Else
        MsgBox "Aucune entité n'a été sélectionnée.", vbExclamation, "Sélection de texte"
        Exit Sub
    End If
    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            Set sourcePolyline = returnObj ' Convertir l'entité en polyligne
            MsgBox "Vous avez sélectionné une polyligne.", vbInformation, "Polyligne sélectionnée"
        Else
            MsgBox "L'entité sélectionnée n'est pas une polyligne.", vbExclamation, "Sélection de polyligne"
            Exit Sub
        End If
    Else
        MsgBox "Aucune entité n'a été sélectionnée.", vbExclamation, "Sélection de polyligne"
        Exit Sub
    End If
    
    ' Demander à l'utilisateur de sélectionner un point pour l'insertion
    ThisDrawing.Utility.GetEntity returnObj, basePnt, "Sélectionnez un point pour l'insertion:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point pour l'insertion.", vbInformation, "Point sélectionné"
        Else
            MsgBox "L'entité sélectionnée n'est pas un point.", vbExclamation, "Sélection de point"
            Exit Sub
        End If
    Else
        MsgBox "Aucune entité n'a été sélectionnée.", vbExclamation, "Sélection de point"
        Exit Sub
    End If
    
    filePath = DestinationFolder & "\" & fileName & ".dxf"
    
    ' Calcule les différences entre les coordonnées du point de base sélectionné et (0,0)
    deltaX = 0 - objPoint.coordinates(0)
    deltaY = 0 - objPoint.coordinates(1)
    
    ' Crée un nouveau fichier DXF
    Set targetDoc = ThisDrawing.Application.Documents.Add(True) ' True pour créer un fichier DXF
    
    ' Récupére les coordonnées de la polyligne source
    Dim coordinates As Variant
    coordinates = sourcePolyline.coordinates
    
    ' Nombre de sommets de la polyligne source
    Dim numVertices As Integer
    numVertices = UBound(coordinates) / 2 + 1
    
    ' Déplace les sommets de la polyligne source en fonction du point d'insertion
    For i = 0 To numVertices - 1
        ' Obtenir les coordonnées actuelles du sommet
        x = coordinates(i * 2)
        y = coordinates(i * 2 + 1)
    
        ' Ajoute les deltas aux coordonnées
        x = x + deltaX
        y = y + deltaY
        
        ' Mettre à jour les nouvelles coordonnées dans le tableau
        coordinates(i * 2) = x
        coordinates(i * 2 + 1) = y
    Next i

    ' Affecter les nouvelles coordonnées à la polyligne source
    sourcePolyline.coordinates = coordinates
    
    ' Copier la polyligne ajustée dans le nouveau fichier DXF
    Set newPolyline = targetDoc.modelSpace.AddLightWeightPolyline(sourcePolyline.coordinates)
    
    ' Ajouter le dernier segment pour fermer la polyligne
    ' Ajouter le dernier segment pour fermer la polyligne
    nVertex(0) = sourcePolyline.coordinates(0): nVertex(1) = sourcePolyline.coordinates(1)
    Debug.Print "Coordonnées du dernier sommet : " & nVertex(0) & ", " & nVertex(1)
    
    newPolyline.AddVertex numVertices - 1, nVertex


    ' Récupérer tous les bulges de la première polyligne
    ReDim bulges(numVertices - 1)

    For i = 0 To numVertices - 1
        ' Récupérer tous les bulges de la première polyligne
        bulges(i) = sourcePolyline.GetBulge(i)
    Next i
    
    ' Réaffecter les bulges à la nouvelle polyligne
    For i = 0 To UBound(bulges)
        newPolyline.SetBulge i, bulges(i)
    Next i
        
    ' Sauvegarder le fichier DXF
    targetDoc.SaveAs filePath, ac2007_dxf  ' Spécifier le format de fichier DXF
    
    ' Fermer le fichier DXF
    targetDoc.Close
End Sub

Attribute VB_Name = "Module17"
'----------------------------------------
' ExportProfilsPline()
' exporte une polyligne de profil dans un fichier dxf
' - demande à l'utilisateur de choisir un texte : typiquement le PM , servira pour construite le nom du fichier
' - demande à l'utilisateur de selectionner une polyligne
' - demande à l'utilisateur de selectionner un point (qui servira de point de base)
' - recupère les éléments de la polyligne
' - récupere les décalages à l'origine
' - recrée une polyligne avec les décalages et la met dans le fichier d'origine
' - reaffecte les arrondis entre les sommets et ferme la polyligne
' - le fichier dxf portera automatiquement le nom equivalent au texte selectionné
' - ATTENTION : ENCORE EN MODE DEVELOPPEMENT : gere pas bien le fait qu'il y ait plusieurs fichiers ouverts au moment du lancement
'----------------------------------------
Sub ExportProfilsPline2()
    Dim targetDoc As AcadDocument
    Dim returnObj As AcadObject
    Dim basePnt As Variant
    Dim sourcePolyline As AcadLWPolyline
    Dim newPolyline As AcadLWPolyline
    Dim objPolyline As AcadLWPolyline
    Dim objText As AcadText
    Dim objPoint As AcadPoint
    Dim i As Integer
    Dim DestinationFolder As String
    Dim fileName As String
    Dim filePath As String
    Dim deltaX As Double, deltaY As Double
    Dim bulges() As Double
    Dim x As Double
    Dim y As Double
    Dim nVertex(0 To 1) As Double
    Dim coordinates As Variant
    Dim numVertices As Integer

    
    ' CONFIGURER ICI LE REPERTOIRE OU SERONT GENERES LES DXF
    DestinationFolder = "c:\data\temp"
    fileName = ""
    filePath = ""
       
     ' Demander à l'utilisateur de sélectionner un texte
    ThisDrawing.Utility.GetEntity returnObj, basePnt, "Sélectionnez un texte:"
    If Not returnObj Is Nothing Then
        If TypeOf returnObj Is AcadText Then
            Set objText = returnObj
            fileName = objText.TextString
            MsgBox "Vous avez sélectionné un texte : " & vbCrLf & fileName, vbInformation, "Texte sélectionné"
        Else
            MsgBox "L'entité sélectionnée n'est pas un texte.", vbExclamation, "Sélection de texte"
            Exit Sub
        End If
    Else
        MsgBox "Aucune entité n'a été sélectionnée.", vbExclamation, "Sélection de texte"
        Exit Sub
    End If
    
    ' Demander à l'utilisateur de sélectionner une polyligne
    ThisDrawing.Utility.GetEntity returnObj, basePnt, "Sélectionnez une polyligne:"
    If Not returnObj Is Nothing Then
        If TypeOf returnObj Is AcadLWPolyline Then
            Set sourcePolyline = returnObj
            MsgBox "Vous avez sélectionné une polyligne.", vbInformation, "Polyligne sélectionnée"
        Else
            MsgBox "L'entité sélectionnée n'est pas une polyligne.", vbExclamation, "Sélection de polyligne"
            Exit Sub
        End If
    Else
        MsgBox "Aucune entité n'a été sélectionnée.", vbExclamation, "Sélection de polyligne"
        Exit Sub
    End If
    
    ' Demander à l'utilisateur de sélectionner un point pour l'insertion
    ThisDrawing.Utility.GetEntity returnObj, basePnt, "Sélectionnez un point pour l'insertion:"
    If Not returnObj Is Nothing Then
        If TypeOf returnObj Is AcadPoint Then
            Set objPoint = returnObj
            MsgBox "Vous avez sélectionné un point pour l'insertion.", vbInformation, "Point sélectionné"
        Else
            MsgBox "L'entité sélectionnée n'est pas un point.", vbExclamation, "Sélection de point"
            Exit Sub
        End If
    Else
        MsgBox "Aucune entité n'a été sélectionnée.", vbExclamation, "Sélection de point"
        Exit Sub
    End If
    
    
    ' Calcule les différences entre les coordonnées du point de base sélectionné et (0,0)
    deltaX = 0 - objPoint.coordinates(0)
    deltaY = 0 - objPoint.coordinates(1)
    
   
 ' Crée un nouvel ensemble de coordonnées basé sur les décalages
    coordinates = sourcePolyline.coordinates
    numVertices = UBound(coordinates) / 2 + 1
    For i = 0 To UBound(coordinates) Step 2
        coordinates(i) = coordinates(i) + deltaX
        coordinates(i + 1) = coordinates(i + 1) + deltaY
    Next i

    
    ' Crée une nouvelle polyligne avec les nouvelles coordonnées
    Set newPolyline = ThisDrawing.modelSpace.AddLightWeightPolyline(coordinates)
    
   ' Sauvegarder le fichier DXF
    filePath = DestinationFolder & "\" & fileName & ".dxf"
  ' Crée un nouveau fichier DXF
    Set targetDoc = ThisDrawing.Application.Documents.Add(True) ' True pour créer un fichier DXF
    ' Copier la polyligne ajustée dans le nouveau fichier DXF
    Set newPolyline = targetDoc.modelSpace.AddLightWeightPolyline(newPolyline.coordinates)
    
    ' Ajouter le dernier segment pour fermer la polyligne
    nVertex(0) = newPolyline.coordinates(0): nVertex(1) = newPolyline.coordinates(1)
      Debug.Print "Coordonnées du dernier sommet : " & nVertex(0) & ", " & nVertex(1)
    newPolyline.AddVertex numVertices - 1, nVertex


    ' Récupérer tous les bulges de la première polyligne
    ReDim bulges(numVertices - 1)
    For i = 0 To numVertices - 1
        ' Récupérer tous les bulges de la première polyligne
        bulges(i) = sourcePolyline.GetBulge(i)
    Next i
    
    ' Réaffecter les bulges à la nouvelle polyligne
    For i = 0 To UBound(bulges)
        newPolyline.SetBulge i, bulges(i)
    Next i
        
    ' on enregistre le tout
    targetDoc.SaveAs filePath, ac2007_dxf  ' Spécifier le format de fichier DXF 2007 comme ca on est tranquille
    
    ' Fermer le fichier DXF
    targetDoc.Close
End Sub

Attribute VB_Name = "Module18"
Sub ExportProfilsPline3()
    Dim targetDoc As AcadDocument
    Dim objSelection As AcadSelectionSet
    Dim obj As AcadObject
    Dim basePnt As Variant
    Dim sourcePolyline As AcadLWPolyline
    Dim newPolyline As AcadLWPolyline
    Dim objText As AcadText
    Dim objPoint As AcadPoint
    Dim i As Integer
    Dim DestinationFolder As String
    Dim fileName As String
    Dim filePath As String
    Dim deltaX As Double, deltaY As Double
    Dim bulges() As Double
    Dim x As Double
    Dim y As Double
    Dim nVertex(0 To 1) As Double
    Dim coordinates As Variant
    Dim numVertices As Integer
    
    ' CONFIGURER ICI LE REPERTOIRE OU SERONT GENERES LES DXF
    DestinationFolder = "c:\data\temp"
    fileName = ""
    filePath = ""
    
    ' Demander à l'utilisateur de sélectionner un texte
    ThisDrawing.Utility.GetEntity objText, basePnt, "Sélectionnez un texte:"
    If Not objText Is Nothing Then
        If TypeOf objText Is AcadText Then
            fileName = objText.TextString
            MsgBox "Vous avez sélectionné un texte : " & vbCrLf & fileName, vbInformation, "Texte sélectionné"
        Else
            MsgBox "L'entité sélectionnée n'est pas un texte.", vbExclamation, "Sélection de texte"
            Exit Sub
        End If
    Else
        MsgBox "Aucune entité n'a été sélectionnée.", vbExclamation, "Sélection de texte"
        Exit Sub
    End If
    
    ' Demander à l'utilisateur de sélectionner une zone pour la sélection par polygone
    ThisDrawing.Utility.GetEntity objSelection, basePnt, "Sélectionnez une zone pour la sélection par polygone:"
    If Not objSelection Is Nothing Then
        If TypeOf objSelection Is AcadSelectionSet Then
            Set objSelection = objSelection.CopyToArray ' Convertir la sélection en tableau d'objets
            ' Parcourir les objets sélectionnés pour trouver la polyligne
            For Each obj In objSelection
                If TypeOf obj Is AcadLWPolyline Then
                    Set sourcePolyline = obj
                    MsgBox "Vous avez sélectionné une polyligne.", vbInformation, "Polyligne sélectionnée"
                    Exit For ' Sortir de la boucle dès qu'une polyligne est trouvée
                End If
            Next obj
        Else
            MsgBox "La sélection n'est pas valide.", vbExclamation, "Sélection invalide"
            Exit Sub
        End If
    Else
        MsgBox "Aucune entité n'a été sélectionnée.", vbExclamation, "Sélection par polygone"
        Exit Sub
    End If
    
    ' Sélectionner un point pour l'insertion
    ThisDrawing.Utility.GetEntity objPoint, basePnt, "Sélectionnez un point pour l'insertion:"
    If Not objPoint Is Nothing Then
        If TypeOf objPoint Is AcadPoint Then
            MsgBox "Vous avez sélectionné un point pour l'insertion.", vbInformation, "Point sélectionné"
        Else
            MsgBox "L'entité sélectionnée n'est pas un point.", vbExclamation, "Sélection de point"
            Exit Sub
        End If
    Else
        MsgBox "Aucune entité n'a été sélectionnée.", vbExclamation, "Sélection de point"
        Exit Sub
    End If
    
    ' Calcule les différences entre les coordonnées du point de base sélectionné et (0,0)
    deltaX = 0 - objPoint.coordinates(0)
    deltaY = 0 - objPoint.coordinates(1)
    
    ' Crée un nouvel ensemble de coordonnées basé sur les décalages
    coordinates = sourcePolyline.coordinates
    numVertices = UBound(coordinates) / 2 + 1
    For i = 0 To UBound(coordinates) Step 2
        coordinates(i) = coordinates(i) + deltaX
        coordinates(i + 1) = coordinates(i + 1) + deltaY
    Next i
    
    ' Crée une nouvelle polyligne avec les nouvelles coordonnées
    Set newPolyline = ThisDrawing.modelSpace.AddLightWeightPolyline(coordinates)
    
    ' Sauvegarder le fichier DXF
    filePath = DestinationFolder & "\" & fileName & ".dxf"
    ' Crée un nouveau fichier DXF
    Set targetDoc = ThisDrawing.Application.Documents.Add(True) ' True pour créer un fichier DXF
    ' Copier la polyligne ajustée dans le nouveau fichier DXF
    Set newPolyline = targetDoc.modelSpace.AddLightWeightPolyline(newPolyline.coordinates)
    
    ' Ajouter le dernier segment pour fermer la polyligne
    nVertex(0) = newPolyline.coordinates(0): nVertex(1) = newPolyline.coordinates(1)
    newPolyline.AddVertex numVertices - 1, nVertex

    ' Récupérer tous les bulges de la première polyligne
    ReDim bulges(numVertices - 1)
    For i = 0 To numVertices - 1
        ' Récupérer tous les bulges de la première polyligne
        bulges(i) = sourcePolyline.GetBulge(i)
    Next i
    
    ' Réaffecter les bulges à la nouvelle polyligne
    For i = 0 To UBound(bulges)
        newPolyline.SetBulge i, bulges(i)
    Next i
        
    ' on enregistre le tout
    targetDoc.SaveAs filePath, ac2007_dxf  ' Spécifier le format de fichier DXF 2007 comme ca on est tranquille
    
    ' Fermer le fichier DXF
    targetDoc.Close
End Sub

Attribute VB_Name = "Module2"
Sub SelectionnerPolyligne()
    Dim objSelection As AcadSelectionSet
    Dim objEntity As AcadEntity
    Dim objPolyline As AcadLWPolyline
    
    ' Demander à l'utilisateur de sélectionner une polyligne
    Set objSelection = ThisDrawing.Utility.GetSelectionSet("Sélectionnez une polyligne:")
    
    ' Vérifier si une polyligne a été sélectionnée
    If Not objSelection Is Nothing Then
        ' Boucler à travers les entités sélectionnées
        For Each objEntity In objSelection
            ' Vérifier si l'entité est une polyligne
            If TypeOf objEntity Is AcadLWPolyline Then
                Set objPolyline = objEntity ' Convertir l'entité en polyligne
                MsgBox "Vous avez sélectionné une polyligne avec " & objPolyline.NumberOfVertices & " sommets.", vbInformation, "Polyligne sélectionnée"
                Exit Sub ' Sortir de la boucle après avoir trouvé une polyligne
            End If
        Next objEntity
        ' Aucune polyligne trouvée parmi les entités sélectionnées
        MsgBox "Aucune polyligne n'a été sélectionnée.", vbExclamation, "Sélection de polyligne"
    Else
        ' Aucune entité sélectionnée
        MsgBox "Aucune entité n'a été sélectionnée.", vbExclamation, "Sélection de polyligne"
    End If
End Sub


Sub Example_GetEntity()
    ' This example creates several objects in model space. It then
    ' prompts the user to select an object. The example continues to
    ' have the user select objects until the user selects in empty space.
    
    ' Create a Ray object in model space
    Dim rayObj As AcadRay
    Dim basepoint(0 To 2) As Double
    Dim SecondPoint(0 To 2) As Double
    basepoint(0) = 3#: basepoint(1) = 3#: basepoint(2) = 0#
    SecondPoint(0) = 1#: SecondPoint(1) = 3#: SecondPoint(2) = 0#
    Set rayObj = ThisDrawing.modelSpace.AddRay(basepoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.modelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.modelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.modelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.modelSpace.AddEllipse(center, majAxis, radRatio)

    ZoomAll
    
    ' Begin the selection
    Dim returnObj As AcadObject
    Dim basePnt As Variant
    
    On Error Resume Next
    
    ' The following example waits for a selection from the user
RETRY:
    ThisDrawing.Utility.GetEntity returnObj, basePnt, "Select an object"
    
    If Err <> 0 Then
        Err.Clear
        MsgBox "Program ended.", , "GetEntity Example"
        Exit Sub
    Else
        returnObj.Update
        MsgBox "The object type is: " & returnObj.EntityName, , "GetEntity Example"
        returnObj.Update
    End If
    
    GoTo RETRY
End Sub

Sub CopierCollerSelection()

    Dim sourceDoc As Object
    Dim targetDoc As Object
    Dim selectedObjects As Object
    
    ' Ouvrir le fichier source et activer la fenêtre
    Set sourceDoc = Documents.Open("C:\data\temp\source.dwg")
    sourceDoc.Activate
    
    ' Sélectionner les objets dans le fichier source
    ' Par exemple, sélectionnez tous les objets dans le modèle
    ThisDrawing.SendCommand "_SELECT" & vbCr
    
    ' Copier les objets sélectionnés
    ThisDrawing.SendCommand "_COPYBASE" & vbCr
    
    ' Fermer le fichier source
    sourceDoc.Close

    ' Ouvrir le fichier cible
    Set targetDoc = Documents.Open("C:\data\temp\cible.dwg")
    targetDoc.Activate
    
     ' Coller les objets dans le fichier cible en définissant le point d'insertion comme (0,0)
    'ThisDrawing.SendCommand "_PASTEBLOCK" & vbCr
    ThisDrawing.SendCommand "_PASTECLIP 0,0" & vbCr

    

    ' Fermer le fichier cible
    targetDoc.Close

End Sub



Sub CopierProfil()

    Dim sourceDoc As Object
    Dim targetDoc As Object
    Dim selectedObjects As Object
    
    ' Ouvrir le fichier source et activer la fenêtre
    Set sourceDoc = Documents.Open("C:\data\temp\source.dwg")
    sourceDoc.Activate
    
    ' Sélectionner les objets dans le fichier source
    ' Par exemple, sélectionnez tous les objets dans le modèle
    ThisDrawing.SendCommand "_SELECT" & vbCr
    
    ' Copier les objets sélectionnés
    ThisDrawing.SendCommand "_COPYBASE" & vbCr
    
    ' Fermer le fichier source
    sourceDoc.Close

    ' Ouvrir le fichier cible
    Set targetDoc = Documents.Open("C:\data\temp\cible.dwg")
    targetDoc.Activate
    
     ' Coller les objets dans le fichier cible en définissant le point d'insertion comme (0,0)
    'ThisDrawing.SendCommand "_PASTEBLOCK" & vbCr
    ThisDrawing.SendCommand "_PASTECLIP 0,0" & vbCr

    

    ' Fermer le fichier cible
    targetDoc.Close

End Sub


Sub testPrompt()
    ThisDrawing.Utility.Prompt "Texte à afficher dans la ligne de commande " & vbCr

End Sub

Attribute VB_Name = "Module3"
Sub SelectionnerEntites()
    Dim objEntity As AcadEntity
    Dim returnObj As AcadObject
    Dim basePnt As Variant

    Dim objPolyline As AcadLWPolyline
    Dim objText As AcadText
    Dim objPoint As AcadPoint
    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            MsgBox "Vous avez sélectionné une polyligne.", vbInformation, "Polyligne sélectionnée"
        Else
            MsgBox "L'entité sélectionnée n'est pas une polyligne.", vbExclamation, "Sélection de polyligne"
        End If
    Else
        MsgBox "Aucune entité n'a été sélectionnée.", vbExclamation, "Sélection de polyligne"
    End If
    
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            MsgBox "Vous avez sélectionné un texte : " & objText.TextString, vbInformation, "Texte sélectionné"
        Else
            MsgBox "L'entité sélectionnée n'est pas un texte.", vbExclamation, "Sélection de texte"
        End If
    Else
        MsgBox "Aucune entité n'a été sélectionnée.", vbExclamation, "Sélection de texte"
    End If
    
    ' Demander à l'utilisateur de sélectionner un point
    ThisDrawing.Utility.GetEntity returnObj, basePnt, "Sélectionnez un point:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point.", vbInformation, "Point sélectionné"
        Else
            MsgBox "L'entité sélectionnée n'est pas un point.", vbExclamation, "Sélection de point"
        End If
    Else
        MsgBox "Aucune entité n'a été sélectionnée.", vbExclamation, "Sélection de point"
    End If
End Sub



Sub SelectionnerEntites2()
    Dim returnObj As AcadObject
    Dim basePnt As Variant

    Dim objPolyline As AcadLWPolyline
    Dim objText As AcadText
    Dim objPoint As AcadPoint
    
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            MsgBox "Vous avez sélectionné une polyligne.", vbInformation, "Polyligne sélectionnée"
        Else
            MsgBox "L'entité sélectionnée n'est pas une polyligne.", vbExclamation, "Sélection de polyligne"
        End If
    Else
        MsgBox "Aucune entité n'a été sélectionnée.", vbExclamation, "Sélection de polyligne"
    End If
    
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            MsgBox "Vous avez sélectionné un texte : " & objText.TextString, vbInformation, "Texte sélectionné"
        Else
            MsgBox "L'entité sélectionnée n'est pas un texte.", vbExclamation, "Sélection de texte"
        End If
    Else
        MsgBox "Aucune entité n'a été sélectionnée.", vbExclamation, "Sélection de texte"
    End If
    
    ' Demander à l'utilisateur de sélectionner un point
    ThisDrawing.Utility.GetEntity returnObj, basePnt, "Sélectionnez un point:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point.", vbInformation, "Point sélectionné"
        Else
            MsgBox "L'entité sélectionnée n'est pas un point.", vbExclamation, "Sélection de point"
        End If
    Else
        MsgBox "Aucune entité n'a été sélectionnée.", vbExclamation, "Sélection de point"
    End If
End Sub

Attribute VB_Name = "Module4"
Sub Example_GetEntity()
    ' This example creates several objects in model space. It then
    ' prompts the user to select an object. The example continues to
    ' have the user select objects until the user selects in empty space.
    
    ' Create a Ray object in model space
    Dim rayObj As AcadRay
    Dim basepoint(0 To 2) As Double
    Dim SecondPoint(0 To 2) As Double
    basepoint(0) = 3#: basepoint(1) = 3#: basepoint(2) = 0#
    SecondPoint(0) = 1#: SecondPoint(1) = 3#: SecondPoint(2) = 0#
    Set rayObj = ThisDrawing.modelSpace.AddRay(basepoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.modelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.modelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.modelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.modelSpace.AddEllipse(center, majAxis, radRatio)

    ZoomAll
    
    ' Begin the selection
    Dim returnObj As AcadObject
    Dim basePnt As Variant
    
    On Error Resume Next
    
    ' The following example waits for a selection from the user
RETRY:
    ThisDrawing.Utility.GetEntity returnObj, basePnt, "Select an object"
    
    If Err <> 0 Then
        Err.Clear
        MsgBox "Program ended.", , "GetEntity Example"
        Exit Sub
    Else
        returnObj.Update
        MsgBox "The object type is: " & returnObj.EntityName, , "GetEntity Example"
        returnObj.Update
    End If
    
    GoTo RETRY
End Sub

Attribute VB_Name = "Module5"
Sub CollerDansNouveauFichier()
    Dim newdoc As AcadDocument
    Dim objSelection As AcadSelectionSet
    Dim copiedObjects As Variant
    Dim obj As AcadObject
    Dim newLayer As AcadLayer
    
    ' Ouvrir le modèle vide pour créer un nouveau dessin
    Set newdoc = ThisDrawing.Application.Documents.Add("C:\data\temp\ModeleVide.dwg")
    
    ' Sélectionner les objets à copier
    ' Assurez-vous que vous avez des objets sélectionnés dans votre dessin avant d'exécuter ce code
    Set objSelection = ThisDrawing.SelectionSets.Add("MySelectionSet")
    objSelection.SelectOnScreen
    
    ' Copier les objets sélectionnés
    ThisDrawing.CopyObjects objSelection, copiedObjects
    
    ' Coller les objets copiés dans le nouveau fichier
    For Each obj In copiedObjects
        ' Ajouter l'objet au dessin actif (nouveau fichier)
        newdoc.modelSpace.AddItem obj
        
        ' Déplacer l'objet vers une nouvelle couche pour éviter les conflits de noms
        Set newLayer = newdoc.Layers.Add("CopiedObjectsLayer")
        obj.Layer = newLayer.Name
    Next obj
    
    ' Effacer la sélection
    objSelection.Delete
End Sub

Attribute VB_Name = "Module6"
Sub CollerDansNouveauFichier()
    Dim objSelection As AcadSelectionSet
    Dim copiedObjects As Variant
    Dim obj As AcadObject
    Dim newdoc As AcadDocument
    Dim newLayer As AcadLayer
    
    ' Vérifier si le jeu de sélection existe déjà et le supprimer le cas échéant
    On Error Resume Next
    ThisDrawing.SelectionSets.Item("MySelectionSet").Delete
    On Error GoTo 0
    
    ' Créer un nouveau jeu de sélection
    Set objSelection = ThisDrawing.SelectionSets.Add("MySelectionSet")
    
    ' Sélectionner les objets à copier
    objSelection.SelectOnScreen
    
    ' Assurer qu'au moins un objet est sélectionné
    If objSelection.Count = 0 Then
        MsgBox "Aucun objet sélectionné. Le processus est annulé.", vbExclamation, "Aucune sélection"
        objSelection.Delete ' Supprimer le jeu de sélection s'il n'y a pas d'objets sélectionnés
        Exit Sub
    End If
    
    ' Créer un nouveau fichier en ouvrant un modèle vide
    Set newdoc = ThisDrawing.Application.Documents.Add("C:\data\temp\ModeleVide.dwg")
    
    ' Copier les objets sélectionnés
    ThisDrawing.CopyObjects objSelection, copiedObjects
    
    ' Coller les objets copiés dans le nouveau fichier
    For Each obj In copiedObjects
        ' Ajouter l'objet au dessin actif (nouveau fichier)
        newdoc.modelSpace.AddItem obj
        
        ' Déplacer l'objet vers une nouvelle couche pour éviter les conflits de noms
        Set newLayer = newdoc.Layers.Add("CopiedObjectsLayer")
        obj.Layer = newLayer.Name
    Next obj
    
    ' Effacer la sélection
    objSelection.Delete
End Sub

Sub Example_SetBulge()
    ' This example creates a lightweight polyline in model space.
    ' It then finds and changes the bulge for a given segment.
    
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a lightweight Polyline object in model space
    Set plineObj = ThisDrawing.modelSpace.AddLightWeightPolyline(points)
    ZoomAll
    
    ' Find the bulge of the third segment
    Dim currentBulge As Double
    currentBulge = plineObj.GetBulge(3)
    MsgBox "The bulge for the third segment is " & plineObj.GetBulge(3), , "SetBulge Example"
    
    ' Change the bulge of the third segment
    plineObj.SetBulge 3, -0.5
    plineObj.Update
    MsgBox "The bulge for the third segment is now " & plineObj.GetBulge(3), , "SetBulge Example"
    
End Sub

Attribute VB_Name = "Module7"
Sub CopyObjectsFromOneFileToAnother1()
    Dim sourceDoc As AcadDocument
    Dim targetDoc As AcadDocument
    Dim objSelection As AcadSelectionSet
    Dim copiedObjects As Variant
    Dim obj As AcadObject
    Dim newLayer As AcadLayer
    
    ' Ouvrir le fichier source
    Set sourceDoc = ThisDrawing.Application.Documents.Open("C:\chemin\vers\fichierSource.dwg")
    
    ' Ouvrir le fichier cible
    Set targetDoc = ThisDrawing.Application.Documents.Open("C:\chemin\vers\fichierCible.dwg")
    
    ' Sélectionner les objets à copier dans le fichier source
    Set objSelection = sourceDoc.SelectionSets.Add("SelectionSet")
    objSelection.SelectOnScreen
    
    ' Copier les objets sélectionnés
    sourceDoc.CopyObjects objSelection, copiedObjects
    
    ' Coller les objets copiés dans le fichier cible
    For Each obj In copiedObjects
        ' Ajouter l'objet à l'espace modèle du fichier cible
        targetDoc.modelSpace.AddItem obj
        
        ' Déplacer l'objet vers une nouvelle couche pour éviter les conflits de noms
        Set newLayer = targetDoc.Layers.Add("CopiedObjectsLayer")
        obj.Layer = newLayer.Name
    Next obj
    
    ' Fermer les fichiers source et cible sans enregistrer les modifications
    sourceDoc.Close False
    targetDoc.Close False
End Sub


Sub CopyObjectsFromActiveFileToAnother()
    Dim targetDoc As AcadDocument
    Dim sourceObj As AcadObject
    Dim copiedObjects As Variant
    'Dim obj As AcadObject
    Dim newLayer As AcadLayer
    Dim objSelection As AcadSelectionSet
        Dim ss As AcadSelectionSet
    Dim returnObj As AcadObject
    Dim basePnt As Variant
    Dim objPolyline As AcadLWPolyline
    Dim objText As AcadText
    Dim objPoint As AcadPoint
    Dim PMfichier As String
     Dim pickedObj As Variant
    
    ' Supprimer le jeu de sélection s'il existe déjà
    On Error Resume Next
    ThisDrawing.SelectionSets.Item("CopySelection").Delete
    ThisDrawing.SelectionSets.Item("MaSelectionSet").Delete
    On Error GoTo 0
    
      ' Créer un jeu de sélection pour les objets à copier
    Set objSelection = ThisDrawing.SelectionSets.Add("CopySelection")
    Set ss = ThisDrawing.SelectionSets.Add("MaSelectionSet") ' Créez un nouveau SelectionSet ou utilisez-en un existant

   
    ' Demander à l'utilisateur de sélectionner une polyligne
    ThisDrawing.Utility.GetEntity returnObj, basePnt, "Sélectionnez une polyligne:"

    ' Vérifier si une entité a été sélectionnée
    If Not returnObj Is Nothing Then
        ' Vérifier si l'entité sélectionnée est une polyligne
        If TypeOf returnObj Is AcadLWPolyline Then
            Set objPolyline = returnObj ' Convertir l'entité en polyligne
            MsgBox "Vous avez sélectionné une polyligne.", vbInformation, "Polyligne sélectionnée"
             ' Ajoutez l'objet à la sélection
           ' returnObj.Select
            ss.Select acSelectionSetAll, returnObj
    
        Else
            MsgBox "L'entité sélectionnée n'est pas une polyligne.", vbExclamation, "Sélection de polyligne"
        End If
    Else
        MsgBox "Aucune entité n'a été sélectionnée.", vbExclamation, "Sélection de polyligne"
    End If
    
    ' Demander à l'utilisateur de sélectionner un texte
    ThisDrawing.Utility.GetEntity returnObj, basePnt, "Sélectionnez un texte:"
    
    ' Vérifier si une entité a été sélectionnée
    If Not returnObj Is Nothing Then
        ' Vérifier si l'entité sélectionnée est un texte
        If TypeOf returnObj Is AcadText Then
            Set objText = returnObj ' Convertir l'entité en texte
            MsgBox "Vous avez sélectionné un texte : " & objText.TextString, vbInformation, "Texte sélectionné"
            PMfichier = objText.TextString
        Else
            MsgBox "L'entité sélectionnée n'est pas un texte.", vbExclamation, "Sélection de texte"
        End If
    Else
        MsgBox "Aucune entité n'a été sélectionnée.", vbExclamation, "Sélection de texte"
    End If
    
    ' Demander à l'utilisateur de sélectionner un point
    ThisDrawing.Utility.GetEntity returnObj, basePnt, "Sélectionnez un point:"
    
    ' Vérifier si une entité a été sélectionnée
    If Not returnObj Is Nothing Then
        ' Vérifier si l'entité sélectionnée est un point
        If TypeOf returnObj Is AcadPoint Then
            Set objPoint = returnObj ' Convertir l'entité en point
            MsgBox "Vous avez sélectionné un point.", vbInformation, "Point sélectionné"
        Else
            MsgBox "L'entité sélectionnée n'est pas un point.", vbExclamation, "Sélection de point"
        End If
    Else
        MsgBox "Aucune entité n'a été sélectionnée.", vbExclamation, "Sélection de point"
    End If

       ' Ouvrir le fichier cible
    Set targetDoc = ThisDrawing.Application.Documents.Add("C:\data\temp\fichierCible.dwg")
    
   Dim selectedObjects() As Variant
ReDim selectedObjects(1 To ss.Count) As Variant

Dim i As Integer

For i = 1 To ss.Count
    selectedObjects(i) = ss.Item(i)
Next i

        
        ' Copier les objets sélectionnés dans le presse-papiers
      ' Créer une collection pour les objets à copier
    Dim objCollection As Object
    Set objCollection = ThisDrawing.Application.GetInterfaceObject("AeccXUiLand.AeccUiLandCopyObjects")
    If objCollection Is Nothing Then
        MsgBox "Impossible d'obtenir l'interface d'objet pour la copie d'objets.", vbExclamation
        Exit Sub
    End If
    
    ' Ajouter les objets sélectionnés à la collection
    Dim obj As AcadObject

For i = 0 To selectedObjects.Count - 1
    objCollection.Add selectedObjects.Item(i)
Next i

    
    ' Copier les objets dans le presse-papiers
    objCollection.CopyObjects
    
    ' Ouvrir le document cible
Set targetDoc = ThisApplication.Documents.Add

' Enregistrez le document sous forme de fichier DXF
targetDoc.SaveAs "c:\data\temp\fic.dxf"

    
    ' Coller les objets copiés dans l'espace modèle du document cible
    targetDoc.SendCommand "_pasteclip" & vbCr
    
    ' Nettoyer le presse-papiers
    ThisDrawing.Application.SetClipboardData Nothing

    
    ' Fermer le fichier cible sans enregistrer les modifications
    targetDoc.Close False
End Sub

Attribute VB_Name = "Module8"
Sub CopierCollerObjets()
    Dim copiedObjects As Variant
    Dim pastePoint As Variant
    
    ' Sélectionner les objets à copier
    MsgBox "Sélectionnez les objets à copier."
    ThisDrawing.SendCommand "_COPY" & vbCr
    
    ' Spécifier le point d'insertion pour le collage
    pastePoint = ThisDrawing.Utility.GetPoint(, "Spécifiez le point d'insertion :")
    
    ' Coller les objets copiés
    MsgBox "Cliquez pour coller les objets copiés."
    ThisDrawing.SendCommand "_PASTE" & vbCr
End Sub




Function PathSeparator() As String
    If Left(Application.Path, 1) = "\" Then
        PathSeparator = "\"
    Else
        PathSeparator = "/"
    End If
End Function

Sub CreerNouveauDWG()
    ' Construire le chemin complet vers le modèle DWG vierge
    Dim cheminModele As String
    Dim sep As String
    sep = PathSeparator() ' Utilisez la fonction PathSeparator pour obtenir le séparateur de répertoire approprié
    cheminModele = "C:" & sep & "Chemin" & sep & "vers" & sep & "Votre" & sep & "ModeleVierge.dwg"

    ' Créez un nouveau document DWG à partir d'un modèle vierge
    Dim newdoc As AcadDocument
    Set newdoc = ThisDrawing.Application.Documents.Add(cheminModele)

    ' Assurez-vous que le nouveau document est actif
    newdoc.Activate

    ' Autres opérations sur le nouveau document...
End Sub

Sub CreateDXFFile()
    Dim acadApp As Object
    Dim acadDoc As Object
    Dim modelSpace As Object
    Dim newEntity As Object
    
    ' Créer une nouvelle instance d'AutoCAD
    Set acadApp = CreateObject("AutoCAD.Application")
    acadApp.Visible = True ' Optionnel : Rendre AutoCAD visible
    
    ' Ouvrir un nouveau document
    Set acadDoc = acadApp.Documents.Add
    
    ' Récupérer l'espace modèle
    Set modelSpace = acadDoc.modelSpace
    
    ' Créer et ajouter des entités (exemple : une ligne et un cercle)
    'Set newEntity = modelSpace.AddLine(Array(0, 0, 0), Array(10, 10, 0))
    'Set newEntity = modelSpace.AddCircle(Array(5, 5, 0), 3)
    
    ' Enregistrer le document en tant que fichier DXF
    Dim savePath As String
    savePath = "C:\data\temp\fichier.dxf"
    acadDoc.SaveAs savePath, "DXF"
    
    ' Fermer AutoCAD
    acadApp.Quit
End Sub

Sub CreerNouveauDXF()
    Dim doc As Object
    Dim chemin As String
    
    ' Créer une nouvelle instance d'AutoCAD
    Set doc = CreateObject("AutoCAD.Application")
    
    ' Activer AutoCAD
    doc.Visible = True
    
    ' Créer un nouveau dessin
    doc.Documents.Add
    
    ' Chemin et nom du fichier DXF à enregistrer
    chemin = "C:\data\temp\NouveauFichier.dxf"
    
    ' Enregistrer le dessin au format DXF
    doc.ActiveDocument.SaveAs chemin, 12 ' 12 correspond au format DXF
    
    ' Fermer AutoCAD
    doc.Quit
End Sub

Sub ImportDXFContents()
    Dim filePath As String
    Dim fileContents As String
    Dim fileNum As Integer
    Dim lineText As String
    Dim dataArray() As String
    Dim pointsArray() As String
    Dim points() As Double
    Dim i As Integer, j As Integer
    Dim element As Variant
    
   ' Demander à l'utilisateur de choisir un répertoire
    filePath = SelectFolder("Sélectionnez un répertoire contenant des fichiers DXF", "")

    ' Vérifier si un répertoire a été sélectionné
    If filePath = "" Then
        MsgBox "repertoire invalide"
        Exit Sub
    End If
    
    ' Ouvrir le fichier DXF
    fileNum = FreeFile
    Open filePath For Input As #fileNum
    fileContents = Input$(LOF(fileNum), fileNum)
    Close #fileNum
    
    ' Séparer le contenu du fichier ligne par ligne
    dataArray = Split(fileContents, vbCrLf)
    
    ' Initialiser un tableau pour stocker les coordonnées des points de la polyligne
    ReDim points(0 To 2)
    
    ' Parcourir chaque ligne du fichier DXF
    For Each element In dataArray
        lineText = CStr(element)
        ' Vérifier si la ligne contient des informations sur une polyligne
        If Left(lineText, 10) = "POLYLINE  " Then
            ' Réinitialiser le tableau des points
            ReDim points(0 To 2)
            j = 0
            
            ' Rechercher les points de la polyligne
            Do While InStr(lineText, " 10") > 0
                ' Extraire les coordonnées X et Y du point
                points(0) = Val(Mid(lineText, InStr(lineText, " 10") + 4, 255))
                points(1) = Val(Mid(lineText, InStr(lineText, " 20") + 4, 255))
                
                ' Stocker les coordonnées du point dans un tableau
                ReDim Preserve pointsArray(j)
                pointsArray(j) = points(0) & "," & points(1)
                
                ' Passer au point suivant
                j = j + 1
                
                ' Rechercher le prochain point
                lineText = Mid(lineText, InStr(lineText, " 10") + 1)
            Loop
            
            ' Créer une polyligne dans AutoCAD avec les coordonnées extraites
            Dim newPolyline As AcadLWPolyline
            Set newPolyline = ThisDrawing.modelSpace.AddLightWeightPolyline(pointsArray)
        End If
    Next element
    
    MsgBox "Importation terminée avec succès !", vbInformation
End Sub

Attribute VB_Name = "Module9"
Sub RenommerFichiersDXF()
    Dim cheminRepertoire As String
    Dim prefixe As String
    Dim suffixe As String
    Dim fichier As String
    Dim nouveauNom As String
    Dim espaceIndex As Integer
    
    ' Demander à l'utilisateur de sélectionner le répertoire à traiter
    With Application.FileDialog(msoFileDialogFolderPicker)
        .Title = "Sélectionner le répertoire à traiter"
        If .show = -1 Then
            cheminRepertoire = .SelectedItems(1)
        Else
            MsgBox "Opération annulée."
            Exit Sub
        End If
    End With
    
    ' Demander à l'utilisateur de saisir le préfixe et le suffixe
    prefixe = InputBox("Entrez le préfixe à supprimer :", "Préfixe")
    suffixe = InputBox("Entrez le suffixe à supprimer (laissez vide si aucun) :", "Suffixe")
    
    ' Vérifier si le répertoire sélectionné existe
    If Dir(cheminRepertoire, vbDirectory) = "" Then
        MsgBox "Le répertoire spécifié n'existe pas."
        Exit Sub
    End If
    
    ' Boucler à travers tous les fichiers .dxf dans le répertoire
    fichier = Dir(cheminRepertoire & "\*.dxf")
    Do While fichier <> ""
        ' Construire le nouveau nom du fichier en supprimant le préfixe, le suffixe et tout ce qui se trouve après le premier espace
        nouveauNom = fichier
        If prefixe <> "" Then
            If Left(nouveauNom, Len(prefixe)) = prefixe Then
                nouveauNom = Mid(nouveauNom, Len(prefixe) + 1)
            End If
        End If
        If suffixe <> "" Then
            If InStr(nouveauNom, suffixe) > 0 Then
                nouveauNom = Left(nouveauNom, InStr(nouveauNom, suffixe) - 1)
            End If
        End If
        espaceIndex = InStr(nouveauNom, " ")
        If espaceIndex > 0 Then
            nouveauNom = Left(nouveauNom, espaceIndex - 1)
        End If
        
        ' Renommer le fichier
        Name cheminRepertoire & "\" & fichier As cheminRepertoire & "\" & nouveauNom
        
        ' Passer au fichier suivant
        fichier = Dir
    Loop
    
    MsgBox "Opération terminée."
End Sub


Sub OuvrirFichierDWG()
    Dim fichier As String
fichier = Application.GetOpenFileName("Fichiers DWG (*.dwg), *.dwg", , "Sélectionnez un fichier DWG")
If fichier <> "False" Then
    ' Le fichier a été sélectionné, vous pouvez procéder à la suite de votre code ici
    MsgBox "Fichier sélectionné : " & fichier
Else
    ' L'utilisateur a annulé la sélection, vous pouvez gérer cela ici
    MsgBox "Aucun fichier sélectionné."
End If

End Sub

Sub FolderSelection1()
    Dim MyPath As String
    MyPath = SelectFolder("Select Folder", "")
    If Len(MyPath) Then
        MsgBox MyPath
    Else
        MsgBox "Cancel was pressed"
    End If
End Sub

'Both arguements are optional. The first is the dialog caption and
'the second is is to specify the top-most visible folder in the
'hierarchy. The default is "My Computer."

Function SelectFolder1(Optional Title As String, Optional TopFolder _
                         As String) As String
    Dim objShell As New Shell32.Shell
    Dim objFolder As Shell32.Folder

'If you use 16384 instead of 1 on the next line,
'files are also displayed
    Set objFolder = objShell.BrowseForFolder _
                            (0, Title, 1, TopFolder)
    If Not objFolder Is Nothing Then
        SelectFolder = objFolder.Items.Item.Path
    End If
End Function


Sub Example_Import2()
    ' This example will create a new drawing. Be sure to save
    ' your work and start a new drawing before running this example.
    ' This example creates a circle. It then exports the drawing
    ' to a file called DXFExprt.DXF. It then opens a new drawing
    ' and imports the file.
    
    ' Create the circle for visual representation
    Dim circleObj As AcadCircle
    Dim centerPt(0 To 2) As Double
    Dim radius As Double
    centerPt(0) = 2: centerPt(1) = 2: centerPt(2) = 0
    radius = 1
    Set circleObj = ThisDrawing.modelSpace.AddCircle(centerPt, radius)
    ZoomAll
    
    ' Create an empty selection set
    Dim sset As AcadSelectionSet
    Set sset = ThisDrawing.SelectionSets.Add("TEST")
    
    ' Export the current drawing to the file specified above.
    Dim exportFile As String
    exportFile = "C:\my documents\DXFExprt"    ' Adjust path for your system
    ThisDrawing.Export exportFile, "DXF", sset
    
    ' Open a new drawing
    Dim Acad As AcadApplication
    Dim newdoc As AcadDocument
    Set Acad = ThisDrawing.Application
    Set newdoc = Acad.Documents.Add("acad.dwt")
    
    ' Define the import
    Dim importFile As String
    Dim InsertPoint(0 To 2) As Double
    Dim scalefactor As Double
    importFile = "C:\my documents\DXFExprt.dxf"  ' Adjust path for your system
    InsertPoint(0) = 0#: InsertPoint(1) = 0#: InsertPoint(2) = 0#
    scalefactor = 2#
    
    ' Import the file
    ThisDrawing.Import importFile, InsertPoint, scalefactor
    ZoomAll
    
End Sub


Function InsererFichierDXF(cheminFichier As String, pointInsertion() As Double, facteurEchelle As Double) As Boolean
    ' Vérifier si le fichier existe
    If Dir(cheminFichier) = "" Then
        MsgBox "Le fichier spécifié n'existe pas.", vbExclamation
        InsererFichierDXF = False
        Exit Function
    End If
    
    ' Construire la commande d'insertion
    Dim commandeInsertion As String
    commandeInsertion = "-INSERER " & """" & cheminFichier & """" & " " & pointInsertion(0) & "," & pointInsertion(1) & "," & pointInsertion(2) & " " & facteurEchelle
    
    ' Envoyer la commande à AutoCAD
    ThisDrawing.Application.ActiveDocument.SendCommand commandeInsertion & vbCr
    
    ' Retourner True si l'insertion a réussi
    InsererFichierDXF = True
End Function


Sub TestInsertionFichierDXF()
    ' Chemin du fichier DXF
    Dim cheminFichier As String
    cheminFichier = "C:\data\temp\fichier.dxf"
    
    ' Point d'insertion et facteur d'échelle
    Dim pointInsertion(0 To 2) As Double
    pointInsertion(0) = 0#: pointInsertion(1) = 0#: pointInsertion(2) = 0#
    Dim facteurEchelle As Double
    facteurEchelle = 1#
    
    ' Appeler la fonction pour insérer le fichier DXF
    If InsererFichierDXF(cheminFichier, pointInsertion, facteurEchelle) Then
        MsgBox "Fichier DXF inséré avec succès !", vbInformation
    Else
        MsgBox "Erreur lors de l'insertion du fichier DXF.", vbExclamation
    End If
End Sub


Sub InsererFichierDXFAvecDecalage(cheminFichier As String, decalageX As Double, decalageY As Double)
    ' Vérifier si le fichier existe
    If Dir(cheminFichier) = "" Then
        MsgBox "Le fichier spécifié n'existe pas.", vbExclamation
        Exit Sub
    End If
    
    Dim InsertionPoint(0 To 2) As Double
    InsertionPoint(0) = decalageX
    InsertionPoint(1) = decalageY
    InsertionPoint(2) = 0#

    
    ' Ouvrir le fichier DXF en tant que référence externe (Xref)
    Dim xref As AcadBlockReference
    Set xref = ThisDrawing.modelSpace.InsertBlock(InsertionPoint, cheminFichier, 0#, 0#, 0#, 0#)
    
    ' Vérifier si l'insertion a réussi
    If xref Is Nothing Then
        MsgBox "Erreur lors de l'insertion du fichier DXF.", vbExclamation
        Exit Sub
    End If
    
    ' Parcourir toutes les entités du fichier DXF
    Dim entite As AcadEntity
    For Each entite In xref.Explode
        ' Ajouter le décalage aux coordonnées de l'entité
        'entite.MoveCoord decalageX, decalageY, 0#
        
        ' Ajouter l'entité ajustée au dessin actif
        ThisDrawing.modelSpace.AddEntity entite
    Next entite
    
    ' Supprimer la référence externe (Xref) du dessin actif
    xref.Delete
End Sub


Sub TestInsertionFichierDXFAvecDecalage()
    ' Chemin du fichier DXF
    Dim cheminFichier As String
    cheminFichier = "c:\data\temp\fichier.dxf"
    
    ' Décalage à appliquer
    Dim decalageX As Double
    Dim decalageY As Double
    decalageX = 10 ' Décalage horizontal
    decalageY = 20 ' Décalage vertical
    
    ' Appeler la fonction pour insérer le fichier DXF avec décalage
    InsererFichierDXFAvecDecalage cheminFichier, decalageX, decalageY
    
    ' Afficher un message de confirmation
    MsgBox "Fichier DXF inséré avec décalage !", vbInformation
End Sub
Function GetDWGFile(ByVal strDir As String, ByVal strTitle As String)
   ' strTitle = "Select Drawing File"
    Dim strFilter As String ' , strTitle As String
    Dim lngFlags As LongPtr, filestring
    strFilter = thAddFilterItem(strFilter, "DWG File (*.dwg)", "*.dwg")
    GetDWGFile = ThisDrawing.ShowOpen(strDir, strFilter, strTitle)
End Function

Sub testGetDWG()
    GetDWGFile "c:\data\temp", "open dwg"
End Sub
