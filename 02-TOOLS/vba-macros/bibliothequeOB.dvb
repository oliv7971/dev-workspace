Attribute VB_Name = "Module1"
Sub CreerPointAvecTaille()
    Dim OldPdmode As Integer
    Dim OldPdsize As Double
    
    ' Sauvegarder les paramètres actuels de style et de taille de point
    OldPdmode = ThisDrawing.GetVariable("PDMODE")
    OldPdsize = ThisDrawing.GetVariable("PDSIZE")
    
    ' Définir le nouveau style de point (0 pour un simple point)
    ThisDrawing.SetVariable "PDMODE", 0
    
    ' Définir la taille du point (ici 5)
    ThisDrawing.SetVariable "PDSIZE", 5
    
    ' Créer un point aux coordonnées (10, 10, 0)
    ThisDrawing.ModelSpace.AddPoint Array(10#, 10#, 0#)
    
    ' Restaurer les paramètres de style et de taille de point d'origine
    ThisDrawing.SetVariable "PDMODE", OldPdmode
    ThisDrawing.SetVariable "PDSIZE", OldPdsize
    
    ' Facultatif : Actualiser l'affichage
    ThisDrawing.Application.ZoomAll
    ThisDrawing.Regen acActiveViewport
End Sub


Sub Example_AddPoint()
    ' This example creates a point in model space.
    Dim pointObj As AcadPoint
    Dim location(0 To 2) As Double
    
    ' Define the location of the point
    location(0) = 5#: location(1) = 5#: location(2) = 0#
    
    ' Create the point
    Set pointObj = ThisDrawing.ModelSpace.AddPoint(location)
    ZoomAll
    End Sub
    
    
    Sub Example_AddLine()
    ' This example adds a line in model space
    
    Dim lineObj As AcadLine
    Dim startPoint(0 To 2) As Double
    Dim endPoint(0 To 2) As Double
    
    ' Define the start and end points for the line
    startPoint(0) = 1#: startPoint(1) = 1#: startPoint(2) = 0#
    endPoint(0) = 5#: endPoint(1) = 5#: endPoint(2) = 0#
    
    ' Create the line in model space
    Set lineObj = ThisDrawing.ModelSpace.AddLine(startPoint, endPoint)
    ZoomAll
    
End Sub

Sub Example_AddPolyline()
    ' This example creates a polyline in model space.
    
    Dim plineObj As AcadPolyline
    Dim points(0 To 14) As Double
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a lightweight Polyline object in model space
    Set plineObj = ThisDrawing.ModelSpace.AddPolyline(points)
    ZoomAll
    
End Sub
  



Sub Example_AddCircle()
    ' This example creates a circle in model space.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
End Sub



Sub Example_AddText()
    ' This example creates a text object in model space.

    Dim textObj As AcadText
    Dim textString As String
    Dim insertionPoint(0 To 2) As Double
    Dim height As Double
    
    ' Define the text object
    textString = "Hello, World."
    insertionPoint(0) = 2: insertionPoint(1) = 2: insertionPoint(2) = 0
    height = 0.5
    
    ' Create the text object in model space
    Set textObj = ThisDrawing.ModelSpace.AddText(textString, insertionPoint, height)
    ZoomAll
    
End Sub

Attribute VB_Name = "Module2"

   Sub SelectionnerPolyligne()
    Dim objSelection As AcadSelectionSet
    Dim objEntity As AcadEntity
    Dim objPolyline As AcadLWPolyline
    
    On Error Resume Next ' Gérer les erreurs si aucune entité n'est sélectionnée
    
    ' Boucle jusqu'à ce qu'une polyligne soit sélectionnée
    Do
        ' Demander à l'utilisateur de sélectionner une polyligne
        Set objSelection = ThisDrawing.Utility.GetSelectionSet("Sélectionnez une polyligne:")
        If Not objSelection Is Nothing Then
            ' Boucler à travers les entités sélectionnées
            For Each objEntity In objSelection
                ' Vérifier si l'entité est une polyligne
                If TypeOf objEntity Is AcadLWPolyline Then
                    Set objPolyline = objEntity ' Convertir l'entité en polyligne
                    MsgBox "Vous avez sélectionné une polyligne avec " & objPolyline.NumberOfVertices & " sommets.", vbInformation, "Polyligne sélectionnée"
                    Exit Sub ' Sortir de la boucle après avoir trouvé une polyligne
                End If
            Next objEntity
            ' Aucune polyligne trouvée parmi les entités sélectionnées
            MsgBox "Aucune polyligne n'a été sélectionnée. Veuillez sélectionner une polyligne.", vbExclamation, "Sélection de polyligne"
        Else
            ' Aucune entité sélectionnée
            MsgBox "Aucune entité n'a été sélectionnée. Veuillez sélectionner une polyligne.", vbExclamation, "Sélection de polyligne"
        End If
    Loop While objSelection Is Nothing ' Répéter jusqu'à ce qu'une polyligne soit sélectionnée
End Sub
