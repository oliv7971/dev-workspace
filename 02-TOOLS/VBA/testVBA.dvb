Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
'-----------------------
'
' On va tester deja vba en dessinant des trucs simples
'
' je sais pas encore si les commandes changent en fonction de la langue (normalement non , contrairement a la ligne de commande
'
'--------------------------
Sub DessinerFormes()
    Dim startPoint(0 To 2) As Double
    Dim endPoint(0 To 2) As Double
    Dim circleCenter(0 To 2) As Double
    Dim circleRadius As Double
    Dim plinePoints(0 To 14) As Double
    Dim pointCoord(0 To 2) As Double
    Dim textPosition(0 To 2) As Double
    
    ' Définir les coordonnées des formes
    startPoint(0) = 0#: startPoint(1) = 0#: startPoint(2) = 0#
    endPoint(0) = 20#: endPoint(1) = 0#: endPoint(2) = 0#
    circleCenter(0) = 10#: circleCenter(1) = 10#: circleCenter(2) = 0#
    circleRadius = 5#
    plinePoints(0) = 0#: plinePoints(1) = 5#: plinePoints(2) = 0#
    plinePoints(3) = 5#: plinePoints(4) = 10#: plinePoints(5) = 0#
    plinePoints(6) = 10#: plinePoints(7) = 5#: plinePoints(8) = 0#
    plinePoints(9) = 15#: plinePoints(10) = 10#: plinePoints(11) = 0#
    plinePoints(12) = 20#: plinePoints(13) = 5#: plinePoints(14) = 0#
    pointCoord(0) = 5#: pointCoord(1) = 5#: pointCoord(2) = 0#
    textPosition(0) = 0#: textPosition(1) = 15#: textPosition(2) = 0#
    
    ' Récupérer l'espace modèle
    Dim modelSpace As AcadModelSpace
    Set modelSpace = ThisDrawing.modelSpace
    
    ' Dessiner la droite
    modelSpace.AddLine startPoint, endPoint
    
    ' Dessiner le cercle
    modelSpace.AddCircle circleCenter, circleRadius
    
    ' Dessiner la polyligne
    Dim pline As AcadLWPolyline
    Set pline = modelSpace.AddLightWeightPolyline(plinePoints)
    
    ' Dessiner le point
    modelSpace.AddPoint pointCoord
    
    ' Dessiner le texte
    Dim text As AcadText
    Set text = modelSpace.AddText("Bonjour", textPosition, 2)
    
End Sub


Sub Example_AddLine()
    ' This example adds a line in model space
    
    Dim lineObj As AcadLine
    Dim startPoint(0 To 2) As Double
    Dim endPoint(0 To 2) As Double
    
    ' Define the start and end points for the line
    startPoint(0) = 1#: startPoint(1) = 1#: startPoint(2) = 0#
    endPoint(0) = 5#: endPoint(1) = 5#: endPoint(2) = 0#
    
    ' Create the line in model space
    Set lineObj = ThisDrawing.modelSpace.AddLine(startPoint, endPoint)
    ZoomAll
    
End Sub
  
Sub Example_AddLightWeightPolyline()
    ' This example creates a lightweight polyline in model space.
    
    Dim plineObj As AcadLWPolyline
    Dim points(0 To 9) As Double
    
    ' Define the 2D polyline points
    points(0) = 1: points(1) = 1
    points(2) = 1: points(3) = 2
    points(4) = 2: points(5) = 2
    points(6) = 3: points(7) = 2
    points(8) = 4: points(9) = 4
        
    ' Create a lightweight Polyline object in model space
    Set plineObj = ThisDrawing.modelSpace.AddLightWeightPolyline(points)
    ZoomAll
    
End Sub
