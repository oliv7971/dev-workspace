Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Sub creerCalque()
    Dim nom_calque As String
    Dim acad_object As Object
    Dim layers As Object
    Dim new_layer As Object
    
    ' Demander à l'utilisateur le nom du nouveau calque
    nom_calque = InputBox("Entrez le nom du nouveau calque :", "Création de calque")
    
    ' Vérifier le nom du calque
    MsgBox "Nom du calque : " & nom_calque
    
    ' Récupération de l'objet AutoCAD
    Set acad_object = GetObject(, "AutoCAD.Application")
    
    ' Récupération de la collection de calques
    Set layers = acad_object.ActiveDocument.layers
    
    ' Création du nouveau calque
    Set new_layer = layers.Add(nom_calque)
    
    If Not new_layer Is Nothing Then
        ' Changer la couleur du calque pour le rendre visuellement actif
        new_layer.color = 1 ' Utilisation de la couleur 1 (rouge) pour le nouveau calque
        
        ' Choisir le nouveau calque
        acad_object.ActiveDocument.ActiveLayer = new_layer
        
        MsgBox "Calque créé et sélectionné avec succès."
    Else
        MsgBox "Erreur lors de la création du calque."
    End If
End Sub
